module comware-netconf 

{

        // the namespace for NETCONF XML definitions is unchanged

        // from RFC 4741 which this document replaces

        namespace "urn:ietf:params:xml:ns:netconf:base:1.0";

        prefix "nc";

        import comware-top-action 

        {

                prefix comware-action;

                revision-date 2014-10-12;

        }

        import comware-top-config 

        {

                prefix comware-config;

                revision-date 2014-10-12;

        }

        import comware-top-data 

        {

                prefix comware-data;

                revision-date 2014-10-12;

        }

        organization "H3C";

                contact "Hangzhou H3C Technologies Co., Ltd.";

        description

                "NETCONF Protocol Data Types and Protocol Operations.

                Copyright (c) 2010 IETF Trust and the persons identified as

                the document authors.  All rights reserved.

                Redistribution and use in source and binary forms, with or

                without modification, is permitted pursuant to, and subject

                to the license terms contained in, the Simplified BSD License

                set forth in Section 4.c of the IETF Trust's Legal Provisions

                Relating to IETF Documents

                (http://trustee.ietf.org/license-info).

                This version of this YANG module is part of RFC XXXX; see

                the RFC itself for full legal notices.";

        // RFC Ed.: replace XXXX with actual RFC number and remove this note

        // RFC Ed.: please update the date to the date of publication

        revision 2019-05-14 

        {

                description "Add cancel-subscription";

        }

        revision 2014-10-12 

        {

                description "Initial revision";

        }

        // NETCONF Standard Protocol Operations

        rpc get-bulk-config 

        {

                description "Retrieve all or part of a specified configuration.";

                reference "h3c";

                input 

                {

                        container source 

                        {

                                description  "The configuration to retrieve.";

                                leaf running 

                                {

                                        type empty;

                                        description "The running configuration is the config source.";

                                }

                        }

                        container filter 

                        {

                                description "Subtree or XPath filter to use.";

                                container top 

                                {

                                        description     "Inline Config content.";

                                        uses comware-config:top-config;

                                }

                        }

                }

                output 

                {

                        anyxml data 

                        {

                                description

                                        "Copy of the source datastore subset which matched

                                        the filter criteria (if any).  An empty data container

                                        indicates that the request did not produce any results.";

                        }

                }

        }

        rpc get-bulk 

        {

                description "Retrieve running configuration and device state information.";

                reference "RFC XXXX, section 7.7.";

                input 

                {

                        container filter 

                        {

                                description "Subtree or XPath filter to use.";

                                container top 

                                {

                                        description     "Inline data content.";

                                        uses comware-data:top-data;

                                }

                        }

                }

                output 

                {

                        anyxml data 

                        {

                                description

                                        "Copy of the running datastore subset and/or state

                                        data which matched the filter criteria (if any).

                                        An empty data container indicates that the request did not

                                        produce any results.";

                        }

                }

        }

        rpc action 

        {

                description

                        "The 'action' operation loads all or part of a specified

                        configuration to the specified target configuration.";

                reference "RFC XXXX, section 7.2.";

                input 

                {

                        leaf error-option 

                        {

                                type enumeration 

                                {

                                        enum stop-on-error 

                                        {

                                                description "The server will stop on errors.";

                                        }

                                        enum continue-on-error 

                                        {

                                                description "The server may continue on errors.";

                                        }

                                }

                                default "stop-on-error";

                                description "The error option to use.";

                        }

                        uses comware-action:top-action;

                }

                output 

                {

                        anyxml data 

                        {

                                description

                                        "Copy of the running datastore subset and/or state

                                        data which matched the filter criteria (if any).

                                        An empty data container indicates that the request did not

                                        produce any results.";

                        }

                }               

    }

        rpc get-sessions 

        {

                description "get-sessions";

    }

        rpc load

        {

                description "load";

                input 

                {

                        leaf file

                        {

                                type string

                                {

                                        length "0..220";

                                        pattern "^[^/ ][^ ]*\.cfg$";

                                }

                        }

                }

        }

        rpc save

        {

                description "save";

                input 

                {

                        leaf file

                        {

                                type string

                                {

                                        length "0..220";

                                        pattern "^[^/ ][^ ]*\.cfg$";

                                }

                        }

                }

        }

        rpc rollback

        {

                description "rollback";

                input 

                {

                        leaf file

                        {

                                type string

                                {

                                        length "0..220";

                                        pattern "^[^/ ][^ ]*\.cfg$";

                                }

                        }

                }

        }

        rpc CLI

        {

                description "CLI";

                input 

                {

                        leaf Configuration

                        {

                                type string

                                {

                                        length "1..65535";

                                }

                        }

                        leaf Execution

                        {

                                type string

                                {

                                        length "1..65535";

                                }

                        }

                }

        }       

        rpc cancel-subscription 

        {

                description "The command to cancel a notification subscription. It

                        takes as argument the name of the notification stream.";

                input 

                {

                        leaf stream 

                        {

                                description "An parameter that indicates which stream of events

                                       will be cancelled.";

                                type string

                                {

                                        length "0..31";

                                        pattern "^([a-zA-Z0-9_-]*)$";

                                }

                        }

                }

        }

}
