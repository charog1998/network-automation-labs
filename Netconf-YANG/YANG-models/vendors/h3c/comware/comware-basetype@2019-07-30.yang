module comware-basetype

{

	namespace "http://www.h3c.com/netconf/basetype:1.0";

	prefix comware-basetype;

	organization "H3C";

	contact "New H3C Technologies Co., Ltd.";

	description "";

	revision 2019-07-30

	{

		description "Synchronize the modification of the schema file to the YANG file.";

	}

	revision 2014-10-12

	{

		description "Initial revision";

	}

	typedef Basetype_MacAddress

	{

		type string

		{

			pattern "(([a-fA-F0-9]{1,2}-){5})([a-fA-F0-9]{1,2})";

		}

		description "MAC address.

					 Additional xml attributes for this type: match, regExp, incremental";

	}

	typedef Basetype_Ipv4Address

	{

	    type string

		{

			pattern "((25[0-5]|2[0-4][0-9]|1[0-9][0-9]|0?[1-9][0-9]|0{0,2}[0-9])\.){3}(25[0-5]|2[0-4][0-9]|1[0-9][0-9]|0?[1-9][0-9]|0{0,2}[0-9])";

		}

		description "IPv4 Address.

					 Additional xml attributes for this type: match, regExp, incremental";

	}

	typedef Basetype_Ipv6Address

	{

		type string;

		description "IPv6 address, with validity check inside.

					 Additional xml attributes for this type: match, regExp, incremental";

	}

	typedef Basetype_IpAddress

	{

		type union

		{

		    type Basetype_Ipv4Address;

			type Basetype_Ipv6Address;

		}

		description "IPv4 or IPv6 address.

					 Additional xml attributes for this type: match, regExp, incremental";

	}

	typedef Basetype_InterfaceName

	{

		type string

		{

			pattern "([a-zA-Z][-a-zA-Z]{1,19}|[a-df-su-zA-DF-SU-Z][-a-zA-Z]{0,19}|((E1|T1|E3|T3) ))(([1-9][0-9]{0,2}|[0-9])/)?(([1-9][0-9]{0,2}|[0-9])/)?(([1-9][0-9]{0,2}|[0-9])/)?([1-9][0-9]{0,4}|[0-9])(:([1-9][0-9]{0,3}|[0-9]))?(\.([1-9][0-9]{0,3}|[0-9]))?";

		}

		description "Interface name. String length constraints must be in range(2..47).

					 Additional xml attributes for this type: match, regExp, incremental";

	}

	typedef Basetype_ObjectIdentifier

	{

		type string;

		description "OID, with validity check inside.

					Additional xml attributes for this type: match, regExp, incremental";

	}

	typedef Basetype_UnsignedInteger32

	{

		type uint32;

		description "Unsigned Integer32.

					Additional xml attributes for this type: match, regExp, incremental";

	}

	typedef Basetype_Integer32

	{

		type int32;

		description "Integer32.

					Additional xml attributes for this type: match, regExp, incremental";

	}

	typedef Basetype_UnsignedInteger64

	{

		type uint64;

		description "Unsigned Integer64.

					Additional xml attributes for this type: match, regExp, incremental";

	}

	typedef Basetype_Integer64

	{

		type int64;

		description "Integer64.

					Additional xml attributes for this type: match, regExp, incremental";

	}

	typedef Basetype_UnsignedShort

	{

		type uint16;

		description "OID, with validity check inside.

					Additional xml attributes for this type: match, regExp, incremental";

	}

	typedef Basetype_Short

	{

		type int16;

		description "Short.

					Additional xml attributes for this type: match, regExp, incremental";

	}

	typedef Basetype_UnsignedChar

	{

		type uint8;

		description "Unsigned Char.

					Additional xml attributes for this type: match, regExp, incremental";

	}

	typedef Basetype_Char

	{

		type int8;

		description "Char.

					Additional xml attributes for this type: match, regExp, incremental";

	}

	typedef Basetype_OctectString

	{

		type string;

		description "Additional xml attributes for this type: match, regExp, incremental";

	}

	typedef Basetype_String

	{

		type string

		{

			pattern "[^?

]*";

		}

		description "String must not contain ?, Tab, and  \r\n characters, but can contain escape characters.

					In xml,the patten is  ^[^?&#x09;&#x0d;&#x0a;]*$

					Additional xml attributes for this type: match, regExp, incremental";

	}

	typedef Basetype_NameString

	{

		type Basetype_String

		{

			pattern

		"([^?

|>]|[^?

>]{2,2}|[^?

]{3,})";

		}

		description "String must not contain ?, Tab, and  \r\n characters, but can contain escape characters excluding > , >> and |.

					In xml,the patten is  ^([^?&#x09;&#x0d;&#x0a;|&gt;]|[^?&#x09;&#x0d;&#x0a;&gt;]{2,2}|[^?&#x09;&#x0d;&#x0a;]{3,})$

					Additional xml attributes for this type: match, regExp, incremental";

	}

	typedef Basetype_Text

	{

		type Basetype_OctectString

		{

			pattern "([^?

 ][^?

]*[^?

 ]|[^?

 ])";

		}

		description "String must not contain ?, Tab, \r\n and escape characters, and must not begin or end with space character.

					In xml,the patten is  ^([^?&#x09;&#x0d;&#x0a; ][^?&#x09;&#x0d;&#x0a;]*[^?&#x09;&#x0d;&#x0a; ]|[^?&#x09;&#x0d;&#x0a; ])$

					Additional xml attributes for this type: match, regExp, incremental";

	}

	typedef Basetype_EncryptString

	{

		type Basetype_OctectString

		{

			pattern "[^?]*";

		}

		description "Additional xml attributes for this type: match, regExp, incremental";

	}

	typedef Basetype_URLString

	{

		type Basetype_OctectString

		{

			pattern "[^?

][^

]*";

		}

		description "String must not contain Tab, \r\n and escape characters, and must not begin with ? character.

					In xml,the patten is  ^[^?&#x09;&#x0d;&#x0a;][^&#x09;&#x0d;&#x0a;]*$

					 Additional xml attributes for this type: match, regExp, incremental";

	}

	typedef Basetype_Boolean

	{

		type boolean;

		description "Additional xml attributes for this type: match, regExp, incremental";

	}

	typedef Basetype_DateTime

	{

		type string

		{

			pattern "[0-9]{4}-[0-1][0-9]-[0-3][0-9]T[0-2][0-9]:[0-5][0-9]:[0-5][0-9](\.[0-9]{1,20})?(Z|[+|-][0-9]{2}:[0-9]{2})?";

		}

		description "Date And Time.

					 Additional xml attributes for this type: match, regExp, incremental";

	}

	typedef Basetype_EnableState

	{

		type enumeration

		{

			enum enable;

			enum disable;

		}

		description "Additional xml attributes for this type: match, regExp, incremental";

	}

	typedef Basetype_OctectString255

	{

		type Basetype_OctectString

		{

			length "0..255";

		}

		description "Additional xml attributes for this type: match, regExp, incremental";

	}

	typedef Basetype_Binary

	{

		type binary;

		description "Additional xml attributes for this type: match, regExp, incremental";

	}

	typedef Basetype_PortList

	{

		type binary

		{

		    length "0..10924";

		}

		description "Additional xml attributes for this type: match, regExp, incremental";

	}

	typedef Basetype_PortRange

	{

		type string;

		description "for example 1, 2-3, 100-200, with validity check inside.

					 Additional xml attributes for this type: match, regExp, incremental";

	}

	typedef Basetype_VlanList

	{

	    type binary

		{

                    length "0..684";

		}

		description "Additional xml attributes for this type: match, regExp, incremental";

	}

	typedef Basetype_VlanRange

	{

		type string;

		description "for example 1, 2-3, 100-200, with validity check inside.

					 Additional xml attributes for this type: match, regExp, incremental";

	}

	typedef Basetype_ContextRange

	{

		type string;

		description "for example 1, 2-3, 100-200, with validity check inside.

					 Additional xml attributes for this type: match, regExp, incremental";

	}

	typedef Basetype_Counter32

	{

		type Basetype_UnsignedInteger32;

		description "Additional xml attributes for this type: match, regExp, incremental";

	}

	typedef Basetype_Counter64

	{

		type Basetype_UnsignedInteger64;

		description "Additional xml attributes for this type: match, regExp, incremental";

	}

	typedef Basetype_Gauge32

	{

		type Basetype_UnsignedInteger32;

		description "Additional xml attributes for this type: match, regExp, incremental";

	}

	typedef Basetype_TimeTicks

	{

		type Basetype_UnsignedInteger32;

		description "Additional xml attributes for this type: match, regExp, incremental";

	}

	typedef Basetype_VRF

	{

		type Basetype_String

		{

			length "0..31";

		}

		description "Additional xml attributes for this type: match, regExp, incremental";

	}

	typedef Basetype_VRFIndex

	{

		type Basetype_UnsignedShort;

		description "Additional xml attributes for this type: match, regExp, incremental";

	}

	typedef Basetype_IfIndex

	{

		type Basetype_UnsignedInteger32;

		description "Additional xml attributes for this type: match, regExp, incremental";

	}

	typedef Basetype_Date

	{

		type string

		{

			pattern "[0-9][0-9][0-9][0-9]-[0-1][0-9]-[0-3][0-9](Z|[+|-][0-2][0-9]:[0-5][0-9])?";

		}

		description "Additional xml attributes for this type: match, regExp, incremental";

	}

	typedef Basetype_Time

	{

		type string

		{

			pattern "[0-2][0-9]:[0-5][0-9]:[0-5][0-9](\\.[0-9]{1,20})?(Z|[+|-][0-9]{2}:[0-9]{2})?";

		}

		description "Additional xml attributes for this type: match, regExp, incremental";

	}

	typedef Basetype_Ipv4Mask

	{

		type string;

		description "Ipv4 Mask, with validity check inside.

					 Additional xml attributes for this type: match, regExp, incremental";

	}

    typedef Basetype_ACLName

	{

		type string

		{

			pattern "([a-zA-Z]{1}.*)";

			length "1..63";

		}

		description "ACL name:length :1-63,case-insensitive,must start with a-z or A-Z

					 Additional xml attributes for this type: match, regExp, incremental";

	}

	typedef Basetype_ACLNumberBasic

	{

		type Basetype_UnsignedInteger32

		{

			range "2000..2999";

		}

		description "basic ACL 2000-2999,

					 Additional xml attributes for this type: match, regExp, incremental";

	}

	typedef Basetype_ACLNumberAdvance

	{

		type Basetype_UnsignedInteger32

		{

			range "3000..3999";

		}

		description "basic advance ACL 3000-3999,

					 Additional xml attributes for this type: match, regExp, incremental";

	}

	typedef Basetype_ACLNumberMAC

	{

		type Basetype_UnsignedInteger32

		{

			range "4000..4999";

		}

		description "Mac ACL 4000-4999,

					 Additional xml attributes for this type: match, regExp, incremental";

	}

	typedef Basetype_ACLNumberCustom

	{

		type Basetype_UnsignedInteger32

		{

			range "5000..5999";

		}

		description "custom-defined ACL 5000-5999,

					 Additional xml attributes for this type: match, regExp, incremental";

	}

	typedef Basetype_ACLNumber

	{

		type Basetype_UnsignedInteger32

		{

			range "2000..5999";

		}

		description "All ACL 2000-5999,

					 Additional xml attributes for this type: match, regExp, incremental";

	}

	typedef Basetype_NameAndIndexUnion

	{

		type union

		{

			type string;

			type uint32;

		}

		description "The union of InterfaceName and IfIndex.

					 Additional xml attributes for this type: match, regExp, incremental";

	}

	typedef Basetype_EmptyString

	{

		type string

		{

			pattern "";

		}

		description "Empty string";

	}

	typedef Basetype_FixedValue

	{

		type string

		{

			pattern "0";

		}

		description "Fixed value";

	}

}
