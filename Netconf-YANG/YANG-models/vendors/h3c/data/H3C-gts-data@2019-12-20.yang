module H3C-gts-data {

    namespace "http://www.h3c.com/netconf/data:1.0";

    prefix "gts-data";

    import comware-basetype {

         prefix "base";

    }

    import comware-extension {

         prefix "ext";

    }

    organization "NEW H3C Technologies Co., Ltd.";

    contact "Website: http://www.h3c.com";

    description "The module entities for gts data.";

    revision 2019-12-20 {

        description "Initial revision.";

    }

    container GTS {

        config false;

        container UserProfileGTS {

            description "This table contains information about User Profile GTS

                This table supports creating rows.";

            list Apply {

                description "Row name";

                key "Name Direction Type Value";

                leaf Name {

                    type base:Basetype_String {

                        length "1..31";

                    }

                    description "User Profile Name";

                }

                leaf Direction {

                    type enumeration {

                        enum 0;

                        enum 1;

                    }

                    description "Application direction";

                }

                leaf Type {

                    type enumeration {

                        enum 1;

                        enum 4;

                    }

                    description "match type";

                }

                leaf Value {

                    type base:Basetype_UnsignedInteger32;

                    description "match value";

                }

                leaf CIR {

                    type base:Basetype_UnsignedInteger32 {

                        range "0..4294967294";

                    }

                    description "committed information rate in kbps";

                }

                leaf CBS {

                    type base:Basetype_UnsignedInteger32 {

                        range "0..4294967294";

                    }

                    description "committed burst size in bytes";

                }

                leaf PIR {

                    type base:Basetype_UnsignedInteger32 {

                        range "0..4294967294";

                    }

                    description "peak information rate in kbps";

                }

                leaf EBS {

                    type base:Basetype_UnsignedInteger32 {

                        range "0..4294967294";

                    }

                    description "excess burst size in bytes";

                }

                leaf Queue-length {

                    type base:Basetype_UnsignedInteger32;

                    description "queue length";

                }

            }

        }

    }

}
