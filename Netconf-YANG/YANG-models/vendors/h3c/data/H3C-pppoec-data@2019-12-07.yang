module H3C-pppoec-data {

    namespace "http://www.h3c.com/netconf/data:1.0";

    prefix "pppoec-data";

    import comware-basetype {

         prefix "base";

    }

    import comware-extension {

         prefix "ext";

    }

    organization "NEW H3C Technologies Co., Ltd.";

    contact "Website: http://www.h3c.com";

    description "The module entities for pppoec data.";

    revision 2019-12-07 {

        description "Initial revision.";

    }

    container PPPOEC {

        config false;

        container PppoecClient {

            list Client {

                key "IfIndex BundleNum";

                leaf IfIndex {

                    type base:Basetype_NameAndIndexUnion;

                }

                leaf BundleNum {

                    type base:Basetype_UnsignedInteger32;

                }

                leaf Hostuniq {

                    type base:Basetype_Boolean;

                }

            }

        }

        container PppoecSpecification {

            leaf MinBundleNum {

                type base:Basetype_UnsignedInteger32;

            }

            leaf MaxBundleNum {

                type base:Basetype_UnsignedInteger32;

            }

        }

    }

}
