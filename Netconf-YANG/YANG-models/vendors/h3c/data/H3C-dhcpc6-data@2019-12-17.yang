module H3C-dhcpc6-data {

    namespace "http://www.h3c.com/netconf/data:1.0";

    prefix "dhcpc6-data";

    import comware-basetype {

         prefix "base";

    }

    import comware-extension {

         prefix "ext";

    }

    organization "NEW H3C Technologies Co., Ltd.";

    contact "Website: http://www.h3c.com";

    description "The module entities for dhcpc6 data.";

    revision 2019-12-17 {

        description "Initial revision.";

    }

    container DHCPC6 {

        config false;

        container DHCPC6Config {

            leaf DSCP {

                type base:Basetype_UnsignedInteger32 {

                    range "0..63";

                }

            }

        }

        container DHCP6Alloc {

            list Alloc {

                key "IfIndex";

                leaf IfIndex {

                    type base:Basetype_NameAndIndexUnion;

                }

                leaf AllocEnable {

                    type base:Basetype_Boolean;

                }

                leaf OptionGroup {

                    type base:Basetype_UnsignedInteger32 {

                        range "1..100";

                    }

                }

                leaf RapidCommit {

                    type base:Basetype_Boolean;

                }

            }

        }

        container DHCP6PrefixDelegation {

            list PrefixDelegation {

                key "IfIndex";

                leaf IfIndex {

                    type base:Basetype_NameAndIndexUnion;

                }

                leaf PrefixNumber {

                    type base:Basetype_UnsignedInteger32 {

                        range "1..1024";

                    }

                }

                leaf OptionGroup {

                    type base:Basetype_UnsignedInteger32 {

                        range "1..100";

                    }

                }

                leaf RapidCommit {

                    type base:Basetype_Boolean;

                }

            }

        }

        container DHCP6Stateless {

            list Stateless {

                key "IfIndex";

                leaf IfIndex {

                    type base:Basetype_NameAndIndexUnion;

                }

                leaf StatelessEnable {

                    type base:Basetype_Boolean;

                }

            }

        }

        container DHCP6ClientInfo {

            list ClientInfo {

                key "IfIndex Type";

                leaf IfIndex {

                    type base:Basetype_NameAndIndexUnion;

                }

                leaf Type {

                    type enumeration {

                        enum 0;

                        enum 1;

                        enum 2;

                    }

                }

                leaf State {

                    type enumeration {

                        enum 0;

                        enum 1;

                        enum 2;

                        enum 3;

                        enum 4;

                        enum 5;

                        enum 6;

                        enum 7;

                        enum 8;

                    }

                }

                leaf IAID {

                    type base:Basetype_String {

                        length "1..10";

                    }

                }

                leaf ClientDUID {

                    type base:Basetype_String {

                        length "1..260";

                    }

                }

                leaf ReachableViaIpv6Address {

                    type base:Basetype_Ipv6Address;

                }

                leaf Ipv6Address {

                    type base:Basetype_Ipv6Address;

                }

                leaf Ipv6PrefixLength {

                    type base:Basetype_UnsignedInteger32 {

                        range "1..128";

                    }

                }

                leaf DNSServer {

                    type base:Basetype_String {

                        length "1..367";

                    }

                }

                leaf DomainName {

                    type base:Basetype_String {

                        length "1..50";

                    }

                }

                leaf PreferredLifetime {

                    type base:Basetype_UnsignedInteger32;

                }

                leaf ValidLifetime {

                    type base:Basetype_UnsignedInteger32;

                }

                leaf T1 {

                    type base:Basetype_UnsignedInteger32;

                }

                leaf T2 {

                    type base:Basetype_UnsignedInteger32;

                }

            }

        }

    }

}
