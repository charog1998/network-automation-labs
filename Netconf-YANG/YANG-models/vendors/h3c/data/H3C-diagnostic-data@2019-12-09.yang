module H3C-diagnostic-data {

    namespace "http://www.h3c.com/netconf/data:1.0";

    prefix "diagnostic-data";

    import comware-basetype {

         prefix "base";

    }

    import comware-extension {

         prefix "ext";

    }

    organization "NEW H3C Technologies Co., Ltd.";

    contact "Website: http://www.h3c.com";

    description "The module entities for diagnostic data.";

    revision 2019-12-09 {

        description "Initial revision.";

    }

    container Diagnostic {

        config false;

        container CPUAlert {

            description "This table contains warnning threshold information about the logical CPUs.";

            list Alert {

                key "Chassis Slot CPUID";

                leaf Chassis {

                    type base:Basetype_UnsignedShort;

                    description "Member ID of the member device where the entity resides.";

                }

                leaf Slot {

                    type base:Basetype_UnsignedShort;

                    description "Slot number of the device node.";

                }

                leaf CPUID {

                    type base:Basetype_UnsignedShort;

                    description "CPU Identification.";

                }

                leaf WarningThreshold {

                    type base:Basetype_UnsignedInteger32 {

                        range "1..100";

                    }

                    description "CPU usage warning threshold(percentage).";

                }

                leaf RecoveryThreshold {

                    type base:Basetype_UnsignedInteger32 {

                        range "0..99";

                    }

                    description "CPU usage recovery threshold(percentage).";

                }

            }

        }

        container MemoryAlert {

            description "This table contains memory information.";

            list Alert {

                key "Chassis Slot CPUID";

                leaf Chassis {

                    type base:Basetype_UnsignedShort;

                    description "Member ID of the member device where the entity resides.";

                }

                leaf Slot {

                    type base:Basetype_UnsignedShort;

                    description "Slot number of the device node.";

                }

                leaf CPUID {

                    type base:Basetype_UnsignedShort;

                    description "CPU Identification.";

                }

                leaf Unit {

                                        type string;

                    description "Unit for memory thresholds";

                }

                leaf MinorThreshold {

                    type base:Basetype_UnsignedInteger32;

                    description "The free memory threshold for minor low memory condition.";

                }

                leaf SevereThreshold {

                    type base:Basetype_UnsignedInteger32;

                    description "The free memory threshold for severe low memory condition.";

                }

                leaf CriticalThreshold {

                    type base:Basetype_UnsignedInteger32;

                    description "The free memory threshold for critical low memory condition..";

                }

                leaf NormalThreshold {

                    type base:Basetype_UnsignedInteger32;

                    description "The free memory threshold for normal low memory condition.";

                }

                leaf EarlyWarningThreshold {

                    type base:Basetype_UnsignedInteger32;

                    description "Early-warning threshold for insufficient-free-memory condition.";

                }

                leaf SecureThreshold {

                    type base:Basetype_UnsignedInteger32;

                    description "Early-warning-removed threshold for insufficient-free-memory condition.";

                }

                leaf CurrentState {

                                        type string;

                    description "The state of memory alert

                        Enumeration.

                        1 Minor

                        2 Severe

                        3 Critical

                        4 Normal

                        5 EarlyWarning

                        6 Secure";

                }

            }

        }

        container CPUGroups {

            description "This table contains usage information about the logical CPUs.";

            list CPUGroup {

                key "Chassis Slot CPUID GroupID";

                leaf Chassis {

                    type base:Basetype_UnsignedShort;

                    description "Member ID of the member device where the entity resides.";

                }

                leaf Slot {

                    type base:Basetype_UnsignedShort;

                    description "Slot number of the device node.";

                }

                leaf CPUID {

                    type base:Basetype_UnsignedShort;

                    description "CPU Identification.";

                }

                leaf GroupID {

                    type base:Basetype_UnsignedShort;

                    description "ID of CPU group.";

                }

                leaf GroupName {

                    type base:Basetype_OctectString {

                        length "1..64";

                    }

                    description "Name of CPU group.";

                }

                leaf CPUUsage {

                    type base:Basetype_UnsignedInteger32 {

                        range "0..100";

                    }

                    description "CPU usage of specified group, and the range of value is 1 to 100.";

                }

                leaf Last1mUsage {

                    type base:Basetype_UnsignedInteger32 {

                        range "0..100";

                    }

                    description "CPU usage of specifyed group in last minute.";

                }

                leaf Last5mUsage {

                    type base:Basetype_UnsignedInteger32 {

                        range "0..100";

                    }

                    description "CPU usage of specifyed group in last 5 minutes.";

                }

            }

        }

        container CPUHistory {

            description "This table contains usage information about the logical CPUs.";

            list CPU {

                key "Chassis Slot CPUID";

                leaf Chassis {

                    type base:Basetype_UnsignedShort;

                    description "Member ID of the member device where the entity resides.";

                }

                leaf Slot {

                    type base:Basetype_UnsignedShort;

                    description "Slot number of the device node.";

                }

                leaf CPUID {

                    type base:Basetype_UnsignedShort;

                    description "CPU Identification.";

                }

                leaf CPUUsage {

                    type base:Basetype_UnsignedInteger32 {

                        range "0..100";

                    }

                    description "CPU usage(percentage).";

                }

                leaf Last1mUsage {

                    type base:Basetype_UnsignedInteger32 {

                        range "0..100";

                    }

                    description "Usage in the most recent 1-minute interval (percentage).";

                }

                leaf Last5mUsage {

                    type base:Basetype_UnsignedInteger32 {

                        range "0..100";

                    }

                    description "Usage in the most recent 5-minute interval (percentage).";

                }

                leaf CPUUsageLimit {

                    type base:Basetype_UnsignedInteger32 {

                        range "0..100";

                    }

                    description "CPU usage threshold(percentage)";

                }

            }

        }

        container Memories {

            description "This table contains memory information.";

            list Memory {

                key "Chassis Slot CPUID";

                leaf Chassis {

                    type base:Basetype_UnsignedShort;

                    description "Member ID of the member device where the entity resides.";

                }

                leaf Slot {

                    type base:Basetype_UnsignedShort;

                    description "Slot number of the device node.";

                }

                leaf CPUID {

                    type base:Basetype_UnsignedShort;

                    description "CPU Identification.";

                }

                leaf Total {

                    type base:Basetype_UnsignedInteger32;

                    description "Total memory size (KB).";

                }

                leaf Used {

                    type base:Basetype_UnsignedInteger32;

                    description "Used memory space (KB).";

                }

                leaf Free {

                    type base:Basetype_UnsignedInteger32;

                    description "Size of the free memory space (KB).";

                }

                leaf FreeRatio {

                    type base:Basetype_OctectString;

                    description "Free memory ratio (%).";

                }

                leaf Buffers {

                    type base:Basetype_UnsignedInteger32;

                    description "Size of the memory space used for buffers (KB).";

                }

                leaf Cached {

                    type base:Basetype_UnsignedInteger32;

                    description "Size of the memory space used for cache (KB).";

                }

                leaf CommitLimit {

                    type base:Basetype_UnsignedInteger64;

                    description "Memory space currently available for allocation (KB).";

                }

                leaf CommittedAS {

                    type base:Basetype_UnsignedInteger64;

                    description "Memory space allocated by processes (KB).";

                }

                leaf VmallocTotal {

                    type base:Basetype_UnsignedInteger64;

                    description "Total allocated virtual memory space (KB).";

                }

                leaf VmallocUsed {

                    type base:Basetype_UnsignedInteger64;

                    description "Used virtual memory space (KB).";

                }

                leaf VmallocChunk {

                    type base:Basetype_UnsignedInteger64;

                    description "Free virtual memory space (KB).";

                }

                leaf SwapTotal {

                    type base:Basetype_UnsignedInteger32;

                    description "Total size of the memory space used for swapping (KB).";

                }

                leaf SwapFree {

                    type base:Basetype_UnsignedInteger32;

                    description "Size of the free memory space used for swapping (KB).";

                }

                leaf LowTotal {

                    type base:Basetype_UnsignedInteger32;

                    description "Total low-memory size (KB).";

                }

                leaf LowFree {

                    type base:Basetype_UnsignedInteger32;

                    description "Free low-memory space (KB).";

                }

                leaf HighTotal {

                    type base:Basetype_UnsignedInteger32;

                    description "Total high-memory size (KB).";

                }

                leaf HighFree {

                    type base:Basetype_UnsignedInteger32;

                    description "Free high-memory space (KB).";

                }

            }

        }

        container CoreAlert {

            description "This table contains warnning threshold information about the logical Cores.";

            list Alert {

                key "Chassis Slot CPUID CoreID";

                leaf Chassis {

                    type base:Basetype_UnsignedShort;

                    description "Member ID of the member device where the entity resides.";

                }

                leaf Slot {

                    type base:Basetype_UnsignedShort;

                    description "Slot number of the device node.";

                }

                leaf CPUID {

                    type base:Basetype_UnsignedShort;

                    description "CPU Identification.";

                }

                leaf CoreID {

                    type base:Basetype_UnsignedShort;

                    description "Core Identification.";

                }

                leaf CoreThreshold {

                    type base:Basetype_UnsignedInteger32;

                    description "Core usage threshold (percentage).";

                }

                leaf Current5SUsage {

                    type base:Basetype_UnsignedInteger32 {

                        range "0..100";

                    }

                    description "CPU usage warning threshold(percentage).";

                }

                leaf Current1MUsage {

                    type base:Basetype_UnsignedInteger32 {

                        range "0..100";

                    }

                    description "CPU usage warning threshold(percentage).";

                }

                leaf Current5MUsage {

                    type base:Basetype_UnsignedInteger32 {

                        range "0..100";

                    }

                    description "CPU usage warning threshold(percentage).";

                }

                leaf LastState {

                                        type string;

                    description "Last alert state..";

                }

            }

        }

        container Configuration {

            description "Get the global configuration of diag module.";

            leaf MonitorDiskEnable {

                type base:Basetype_Boolean;

                description "The disk monitor is enable or not.";

            }

            leaf DefaultMonitorDiskUsageInterval {

                type base:Basetype_UnsignedInteger32 {

                    range "5..1800";

                }

                description "The default disk monitor interval.";

            }

            leaf MonitorDiskUsageInterval {

                type base:Basetype_UnsignedInteger32 {

                    range "5..1800";

                }

                description "The actual disk monitor interval.";

            }

        }

        container DiskAlert {

            description "This table contains the disk information.";

            list Alert {

                key "Chassis Slot CPUID DiskName";

                leaf Chassis {

                    type base:Basetype_UnsignedShort;

                    description "Member ID of the member device where the entity resides.";

                }

                leaf Slot {

                    type base:Basetype_UnsignedShort;

                    description "Slot number of the device node.";

                }

                leaf CPUID {

                    type base:Basetype_UnsignedShort;

                    description "CPU Identification.";

                }

                leaf DiskName {

                    type base:Basetype_NameString {

                        length "1..64";

                    }

                    description "Disk name.";

                }

                leaf Threshold {

                    type base:Basetype_UnsignedInteger32 {

                        range "1..100";

                    }

                    description "Disk usage threshold (percentage).";

                }

            }

        }

    }

}
