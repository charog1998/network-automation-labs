module H3C-vpls-data {

    namespace "http://www.h3c.com/netconf/data:1.0";

    prefix "vpls-data";

    import comware-basetype {

         prefix "base";

    }

    import comware-extension {

         prefix "ext";

    }

    organization "NEW H3C Technologies Co., Ltd.";

    contact "Website: http://www.h3c.com";

    description "The module entities for vpls data.";

    revision 2019-12-09 {

        description "Initial revision.";

    }

    container VPLS {

        config false;

        container SignalingLDPs {

            description "The table descriped Revertive information of PW created by SignalingLDP.

                This table supports creating rows.";

            list SignalingLDP {

                description "Revertive information of PW created by SignalingLDP.";

                key "VsiName";

                leaf VsiName {

                    type base:Basetype_String {

                        length "1..31";

                    }

                    description "Index column VSI name characters 1-31";

                }

                container Revertive {

                    description "Switch traffic back to to the primary PW when it recovers.";

                    leaf Type {

                        type enumeration {

                            enum 1;

                            enum 2;

                        }

                        description "Revertive type, Enumeration：
                              1.never 
                              2.wtr";

                    }

                    leaf Time {

                        type base:Basetype_UnsignedShort {

                            range "0..3600";

                        }

                        description "Time for WTR,Only works when the revertive type is WTR
                              value range 0~3600sec";

                    }

                }

            }

        }

        container RmtMACs {

            description "RmtMACs table

                This table supports creating rows.";

            list MAC {

                description "mac row";

                key "VsiName MacAddr";

                leaf VsiName {

                    type base:Basetype_String;

                    description "Index column, VSI name, characters 1-31";

                }

                leaf MacAddr {

                    type base:Basetype_MacAddress;

                    description "Index column, MAC address";

                }

                leaf LinkID {

                    type base:Basetype_UnsignedInteger32;

                    description "Link ID";

                }

                leaf MACState {

                    type enumeration {

                        enum 0;

                    }

                    description "MAC state, now only support dynamic, Enumeration 0(dynamic)indicates the mac is learned";

                }

                leaf Aging {

                    type base:Basetype_Boolean;

                    description "MAC aging, Aging(true), NotAging(false)";

                }

                leaf AgingTime {

                    type base:Basetype_UnsignedInteger32;

                    description "MAC aging time, the value depends on the device";

                }

            }

        }

        container LDPPeers {

            description "LDPPeers table

                This table supports creating rows.";

            list LDPPeer {

                description "LDPPeer row";

                key "VsiName PeerAddr PWID";

                leaf VsiName {

                    type base:Basetype_String {

                        length "1..31";

                    }

                    description "Index column, VSI name, characters 1-31";

                }

                leaf PeerAddr {

                    type base:Basetype_Ipv4Address;

                    description "ipv4 peer address";

                }

                leaf PWID {

                    type base:Basetype_UnsignedInteger32 {

                        range "1..4294967295";

                    }

                    description "PW ID from 1 to 4294967295";

                }

                leaf Hub {

                    type base:Basetype_Boolean;

                    description "Boolean:
                        true： Hub
                        false：Spoke(default)";

                }

                leaf SplitHorizon {

                    type base:Basetype_Boolean;

                    description "Boolean:
                        true: Enabled(default)
                        false:Disabled";

                }

                leaf PWClass {

                    type base:Basetype_String {

                        length "1..19";

                    }

                    description "PWClass name";

                }

                leaf TunnelPolicy {

                    type base:Basetype_String {

                        length "1..19";

                    }

                    description "TunnelPolicy name";

                }

                leaf Statistics {

                    type base:Basetype_Boolean;

                    description "PW statistics, Boolean:
                        true
                        false(default)";

                }

            }

        }

        container LDPBackupPeers {

            description "LDPBackupPeers table

                This table supports creating rows.";

            list LDPBackupPeer {

                description "LDPBackupPeer row";

                key "VsiName MainPeerAddr MainPWID PeerAddr PWID";

                leaf VsiName {

                    type base:Basetype_String {

                        length "1..31";

                    }

                    description "Index column, VSI name, characters 1-31";

                }

                leaf MainPeerAddr {

                    type base:Basetype_Ipv4Address;

                    description "ipv4 address of main peer";

                }

                leaf MainPWID {

                    type base:Basetype_UnsignedInteger32 {

                        range "1..4294967295";

                    }

                    description "PW ID of main pw ranges from 1 to 4294967295";

                }

                leaf PeerAddr {

                    type base:Basetype_Ipv4Address;

                    description "ipv4 address of backup peer";

                }

                leaf PWID {

                    type base:Basetype_UnsignedInteger32 {

                        range "1..4294967295";

                    }

                    description "PW ID of backup pw ranges from 1 to 4294967295";

                }

                leaf Hub {

                    type base:Basetype_Boolean;

                    description "Boolean:
                        true： Hub
                        false：Spoke(default)";

                }

                leaf SplitHorizon {

                    type base:Basetype_Boolean;

                    description "Boolean:
                        true: Enabled(default)
                        false:Disabled";

                }

                leaf PWClass {

                    type base:Basetype_String {

                        length "1..19";

                    }

                    description "PWClass name";

                }

                leaf TunnelPolicy {

                    type base:Basetype_String {

                        length "1..19";

                    }

                    description "TunnelPolicy name";

                }

                leaf Statistics {

                    type base:Basetype_Boolean;

                    description "PW statistics, Boolean:
                        true
                        false(default)";

                }

            }

        }

        container SignalingStatics {

            description "The table describe Revertive information of PW created by SignalingStatic.

                This table supports creating rows.";

            list SignalingStatic {

                description "Revertive information of PW created by SignalingStatic.";

                key "VsiName";

                leaf VsiName {

                    type base:Basetype_String {

                        length "1..31";

                    }

                    description "Index column VSI name characters 1-31";

                }

                container Revertive {

                    description "Switch traffic back to to the primary PW when it recovers.";

                    leaf Type {

                        type enumeration {

                            enum 1;

                            enum 2;

                        }

                        description "Revertive type, Enumeration:
                              1.never 
                              2.wtr";

                    }

                    leaf Time {

                        type base:Basetype_UnsignedShort {

                            range "0..3600";

                        }

                        description "Time for WTR,Only works when the revertive type is WTR,
                              value range 0~3600sec";

                    }

                }

            }

        }

        container StaticPeers {

            description "StaticPeers table

                This table supports creating rows.";

            list StaticPeer {

                description "StaticPeer row";

                key "VsiName PeerAddr PWID";

                leaf VsiName {

                    type base:Basetype_String {

                        length "1..31";

                    }

                    description "Index column, VSI name, characters 1-31";

                }

                leaf PeerAddr {

                    type base:Basetype_Ipv4Address;

                    description "ipv4 address of peer";

                }

                leaf PWID {

                    type base:Basetype_UnsignedInteger32 {

                        range "1..4294967295";

                    }

                    description "PW ID 1 to 4294967295";

                }

                leaf InLabel {

                    type base:Basetype_UnsignedInteger32;

                    description "InLabel";

                }

                leaf OutLabel {

                    type base:Basetype_UnsignedInteger32;

                    description "OutLabel";

                }

                leaf Hub {

                    type base:Basetype_Boolean;

                    description "Boolean:
                        true： Hub
                        false：Spoke(default)";

                }

                leaf SplitHorizon {

                    type base:Basetype_Boolean;

                    description "Boolean:
                        true: Enabled(default)
                        false:Disabled";

                }

                leaf PWClass {

                    type base:Basetype_String {

                        length "1..19";

                    }

                    description "PWClass name";

                }

                leaf TunnelPolicy {

                    type base:Basetype_String {

                        length "1..19";

                    }

                    description "TunnelPolicy name";

                }

                leaf Statistics {

                    type base:Basetype_Boolean;

                    description "PW statistics, Boolean:
                        true : Enabled
                        false: Disabled(default)";

                }

            }

        }

        container StaticBackupPeers {

            description "StaticBackupPeers table

                This table supports creating rows.";

            list StaticBackupPeer {

                description "StaticBackupPeer row";

                key "VsiName MainPeerAddr MainPWID PeerAddr PWID";

                leaf VsiName {

                    type base:Basetype_String {

                        length "1..31";

                    }

                    description "Index column, VSI name, characters 1-31";

                }

                leaf MainPeerAddr {

                    type base:Basetype_Ipv4Address;

                    description "ipv4 address of main peer";

                }

                leaf MainPWID {

                    type base:Basetype_UnsignedInteger32 {

                        range "1..4294967295";

                    }

                    description "PW ID of main pw ranges from 1 to 4294967295";

                }

                leaf PeerAddr {

                    type base:Basetype_Ipv4Address;

                    description "ipv4 address of backup peer";

                }

                leaf PWID {

                    type base:Basetype_UnsignedInteger32 {

                        range "1..4294967295";

                    }

                    description "PW ID of backup pw ranges from 1 to 4294967295";

                }

                leaf InLabel {

                    type base:Basetype_UnsignedInteger32;

                    description "InLabel";

                }

                leaf OutLabel {

                    type base:Basetype_UnsignedInteger32;

                    description "OutLabel";

                }

                leaf Hub {

                    type base:Basetype_Boolean;

                    description "Boolean:
                        true： Hub
                        false：Spoke(default)";

                }

                leaf SplitHorizon {

                    type base:Basetype_Boolean;

                    description "Boolean:
                        true: Enabled(default)
                        false:Disabled";

                }

                leaf PWClass {

                    type base:Basetype_String {

                        length "1..19";

                    }

                    description "PWClass name";

                }

                leaf TunnelPolicy {

                    type base:Basetype_String {

                        length "1..19";

                    }

                    description "TunnelPolicy name";

                }

                leaf Statistics {

                    type base:Basetype_Boolean;

                    description "PW statistics, Boolean:
                        true
                        false(default)";

                }

            }

        }

        container PWs {

            description "PWs table";

            list PW {

                description "PW row";

                key "VsiName PeerAddr PWID";

                leaf VsiName {

                    type base:Basetype_String {

                        length "1..31";

                    }

                    description "Vsi name which the pw belongs to";

                }

                leaf PeerAddr {

                    type base:Basetype_Ipv4Address;

                    description "ipv4 address of peer";

                }

                leaf PWID {

                    type base:Basetype_UnsignedInteger32 {

                        range "1..4294967295";

                    }

                    description "PW ID 1 to 4294967295";

                }

                leaf Protocol {

                    type enumeration {

                        enum 1;

                        enum 2;

                    }

                    description "Protocol enumeration:
                        1:STATIC
                        2:LDP";

                }

                leaf InLabel {

                    type base:Basetype_UnsignedInteger32;

                    description "InLabel, the value depends on the device";

                }

                leaf OutLabel {

                    type base:Basetype_UnsignedInteger32;

                    description "OutLabel, the value depends on the device";

                }

                leaf MTU {

                    type base:Basetype_UnsignedInteger32;

                    description "VSI mtu";

                }

                leaf TunnelGroupID {

                    type base:Basetype_UnsignedInteger64;

                    description "TunnelGroupID";

                }

                container TunnelNHLFEIDs {

                    description "next hop label forwarding entry, Repeat supported";

                    leaf-list TunnelNHLFEID {

                        type base:Basetype_UnsignedInteger32;

                    }

                }

                leaf IsMainPW {

                    type base:Basetype_Boolean;

                    description "true - Main PW, false - Backup PW";

                }

                leaf HubSpoke {

                    type enumeration {

                        enum 0;

                        enum 1;

                        enum 2;

                    }

                    description "Hub -Spoke 
                        true -Hub.
                        false -Spoke(default).";

                }

                leaf SplitHorizon {

                    type base:Basetype_Boolean;

                    description "Boolean:
                        true: Enabled(default)
                        false:Disabled";

                }

                leaf ControlWord {

                    type base:Basetype_Boolean;

                    description "Boolean:
                        true: Enabled
                        false:Disabled";

                }

                leaf PWType {

                    type base:Basetype_UnsignedInteger32 {

                        range "0..25";

                    }

                    description "PW encapsulation type, Enumeration:
                        0 Unknown
                        1 FR_DLCI_MARTINI
                        2 ATM_AAL5_SDU_VCC
                        3 ATM_CELL_TRANSPORT
                        4 VLAN
                        5 ETHERNET
                        6 HDLC
                        7 PPP
                        8 CESOM
                        9 ATM_CELL_VCC
                        10 ATM_CELL_VPC
                        11 IP_INTERWORKING
                        12 ATM_CELL_1TO1_VCC
                        13 ATM_CELL_1TO1_VPC
                        14 ATM_AAL5_PDU_VCC
                        15 FR_PORT
                        16 CEP
                        17 TDM_SATOP_E1
                        18 TDM_SATOP_T1
                        19 TDM_SATOP_E3
                        20 TDM_SATOP_T3
                        21 TDM_CESOPSN_BASIC
                        22 TDMoIP_AAL1_Mode
                        23 TDM_CESOPSN_WITH_CAS
                        24 TDMoIP_AAL2_Mode
                        25 FR_DLCI";

                }

                leaf LinkID {

                    type base:Basetype_UnsignedInteger32;

                    description "Link ID of the PW";

                }

                leaf State {

                    type base:Basetype_UnsignedInteger32 {

                        range "1..6";

                    }

                    description "PW state, Enumeration:
                        1: UP
                        2: DOWN
                        3: Blocked
                        4: Ddfect
                        5: Idle
                        6: Duplicate";

                }

                container InputStatistics {

                    description "Input statistcs:
                        Octets:  Packet octets of input
                        Packets: Packet number of input
                        Errors:  Error packet number of input
                        Discards:Discarded packet number of input";

                    leaf Octets {

                        type base:Basetype_UnsignedInteger64;

                    }

                    leaf Packets {

                        type base:Basetype_UnsignedInteger64;

                    }

                    leaf Errors {

                        type base:Basetype_UnsignedInteger64;

                    }

                    leaf Discards {

                        type base:Basetype_UnsignedInteger64;

                    }

                }

                container OutputStatistics {

                    description "Output statistics:
                        Octets:  Packet octets of output
                        Packets: Packet number of output
                        Errors:  Error packet number of output
                        Discards:Discarded packet number of output";

                    leaf Octets {

                        type base:Basetype_UnsignedInteger64;

                    }

                    leaf Packets {

                        type base:Basetype_UnsignedInteger64;

                    }

                    leaf Errors {

                        type base:Basetype_UnsignedInteger64;

                    }

                    leaf Discards {

                        type base:Basetype_UnsignedInteger64;

                    }

                }

            }

        }

    }

}
