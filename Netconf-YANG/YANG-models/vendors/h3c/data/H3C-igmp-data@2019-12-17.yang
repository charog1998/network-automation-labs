module H3C-igmp-data {

    namespace "http://www.h3c.com/netconf/data:1.0";

    prefix "igmp-data";

    import comware-basetype {

         prefix "base";

    }

    import comware-extension {

         prefix "ext";

    }

    organization "NEW H3C Technologies Co., Ltd.";

    contact "Website: http://www.h3c.com";

    description "The module entities for igmp data.";

    revision 2019-12-17 {

        description "Initial revision.";

    }

    container IGMP {

        config false;

        container Interfaces {

            description "IGMP interface information table";

            list Interface {

                description "Row name";

                key "IfIndex";

                leaf IfIndex {

                    type base:Basetype_NameAndIndexUnion;

                    description "Interface index";

                }

                leaf Enabled {

                    type base:Basetype_Boolean;

                    description "IGMP enable status";

                }

                leaf Version {

                    type enumeration {

                        enum 1;

                        enum 2;

                        enum 3;

                    }

                    description "IGMP version";

                }

            }

        }

        container Groups {

            description "IGMP group information table";

            list Group {

                description "Row name";

                key "IfIndex GroupAddr";

                leaf IfIndex {

                    type base:Basetype_NameAndIndexUnion;

                    description "Interface index";

                }

                leaf GroupAddr {

                    type base:Basetype_Ipv4Address;

                    description "Group address";

                }

                leaf Uptime {

                    type base:Basetype_TimeTicks;

                    description "Uptime in seconds";

                }

                leaf Expires {

                    type base:Basetype_TimeTicks;

                    description "Expire time in seconds";

                }

            }

        }

        container SrcList {

            description "IGMP group source information table";

            list Src {

                description "Row name";

                key "IfIndex GroupAddr SourceAddr";

                leaf IfIndex {

                    type base:Basetype_NameAndIndexUnion;

                    description "Interface index";

                }

                leaf GroupAddr {

                    type base:Basetype_Ipv4Address;

                    description "Group address";

                }

                leaf SourceAddr {

                    type base:Basetype_Ipv4Address;

                    description "Source address";

                }

                leaf Uptime {

                    type base:Basetype_TimeTicks;

                    description "Uptime in seconds";

                }

                leaf Expires {

                    type base:Basetype_TimeTicks;

                    description "Expire time in seconds";

                }

            }

        }

        container HostInterfaces {

            description "IGMP host interface information table";

            list Interface {

                description "Row name";

                key "IfIndex";

                leaf IfIndex {

                    type base:Basetype_NameAndIndexUnion;

                    description "Interface index";

                }

                leaf Enabled {

                    type base:Basetype_Boolean;

                    description "IGMP host enable status";

                }

            }

        }

    }

}
