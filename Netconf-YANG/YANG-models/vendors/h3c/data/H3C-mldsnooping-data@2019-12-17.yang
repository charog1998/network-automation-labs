module H3C-mldsnooping-data {

    namespace "http://www.h3c.com/netconf/data:1.0";

    prefix "mldsnooping-data";

    import comware-basetype {

         prefix "base";

    }

    import comware-extension {

         prefix "ext";

    }

    organization "NEW H3C Technologies Co., Ltd.";

    contact "Website: http://www.h3c.com";

    description "The module entities for mldsnooping data.";

    revision 2019-12-17 {

        description "Initial revision.";

    }

    container MLDSnooping {

        config false;

        container Configuration {

            description "MLD Snooping global information table

                This table supports creating rows.";

            leaf Enabled {

                type base:Basetype_EnableState;

                description "Enable global MLD Snooping";

            }

        }

        container VLANs {

            description "MLD Snooping VLAN information table";

            list VLAN {

                description "Row name";

                key "VLANID";

                leaf VLANID {

                    type base:Basetype_UnsignedShort {

                        range "1..4094";

                    }

                    description "VLAN id";

                }

                leaf Enabled {

                    type base:Basetype_EnableState;

                    description "Enable MLD Snooping on the VLAN";

                }

                leaf Version {

                    type enumeration {

                        enum 1;

                        enum 2;

                    }

                    description "Specify version";

                }

                leaf DropUnknown {

                    type base:Basetype_EnableState;

                    description "Configure drop-unknown";

                }

                leaf Querier {

                    type base:Basetype_EnableState;

                    description "Enable the querier function";

                }

                leaf QueryInterval {

                    type base:Basetype_UnsignedShort {

                        range "2..31744";

                    }

                    description "Set the interval between general queries";

                }

                leaf GeneralQuerySourceAddr {

                    type base:Basetype_Ipv6Address;

                    description "Configure the source address of general queries";

                }

                leaf SpecialQuerySourceAddr {

                    type base:Basetype_Ipv6Address;

                    description "Configure the source address of group-specific";

                }

            }

        }

        container FastLeavePorts {

            description "MLD Snooping port fast leave information table";

            list Interface {

                description "Row name";

                key "IfIndex";

                leaf IfIndex {

                    type base:Basetype_NameAndIndexUnion;

                    description "Interface index";

                }

                leaf FastLeaveVlanList {

                    type base:Basetype_VlanRange;

                    description "Config fast leave vlan list";

                }

            }

        }

        container GroupLimitPorts {

            description "MLD Snooping port group limit information table

                This table supports creating rows.";

            list Interface {

                description "Row name";

                key "IfIndex Limit";

                leaf IfIndex {

                    type base:Basetype_NameAndIndexUnion;

                    description "Interface index";

                }

                leaf Limit {

                    type base:Basetype_UnsignedInteger32;

                    description "Group limit number";

                }

                leaf GroupLimitVlanList {

                    type base:Basetype_VlanRange;

                    description "Config group limit vlan list";

                }

            }

        }

        container IPv6Layer2MulticastGroups {

            description "Show MLD Snooping groups information table";

            list VLAN {

                description "Row name";

                key "VLANID GroupAddr SourceAddr IfIndex";

                leaf VLANID {

                    type base:Basetype_UnsignedShort {

                        range "1..4094";

                    }

                    description "VLAN id";

                }

                leaf GroupAddr {

                    type base:Basetype_Ipv6Address;

                    description "Special the group address";

                }

                leaf SourceAddr {

                    type base:Basetype_Ipv6Address;

                    description "Special the source address";

                }

                leaf IfIndex {

                    type base:Basetype_NameAndIndexUnion;

                    description "Show the port of the group and source";

                }

            }

        }

    }

}
