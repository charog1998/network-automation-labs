module H3C-staticroute-data {

    namespace "http://www.h3c.com/netconf/data:1.0";

    prefix "staticroute-data";

    import comware-basetype {

         prefix "base";

    }

    import comware-extension {

         prefix "ext";

    }

    organization "NEW H3C Technologies Co., Ltd.";

    contact "Website: http://www.h3c.com";

    description "The module entities for staticroute data.";

    revision 2019-12-17 {

        description "Synchronize the modification of the schema file to the YANG file.";

    }

    revision 2016-07-15 {

        description "Initial revision.";

    }

    container StaticRoute {

        config false;

        container Ipv4StaticRouteConfigurations {

            description "IPv4 static route running information.

                This table supports creating rows.";

            list RouteEntry {

                description "Row name of Ipv4StaticRouteConfigurations table.";

                key "DestVrfIndex DestTopologyIndex Ipv4Address Ipv4PrefixLength NexthopVrfIndex NexthopIpv4Address IfIndex";

                leaf DestVrfIndex {

                    type union {

                        type base:Basetype_EmptyString;

                        type base:Basetype_NameAndIndexUnion;

                    }

                    description "Destination VRF index.";

                }

                leaf DestTopologyIndex {

                    type base:Basetype_UnsignedInteger32;

                    description "Destination topology index.";

                }

                leaf Ipv4Address {

                    type base:Basetype_Ipv4Address;

                    description "Destination IPv4 address.";

                }

                leaf Ipv4PrefixLength {

                    type base:Basetype_UnsignedChar {

                        range "0..32";

                    }

                    description "Length of the destination IPv4 address prefix.";

                }

                leaf NexthopVrfIndex {

                    type union {

                        type base:Basetype_EmptyString;

                        type base:Basetype_NameAndIndexUnion;

                    }

                    description "Nexthop VRF index.";

                }

                leaf NexthopIpv4Address {

                    type base:Basetype_Ipv4Address;

                    description "Nexthop IPv4 address.";

                }

                leaf IfIndex {

                    type union {

                        type base:Basetype_EmptyString;

                        type base:Basetype_NameAndIndexUnion;

                    }

                    description "Out interface index.";

                }

                leaf Tag {

                    type base:Basetype_UnsignedInteger32 {

                        range "0..4294967295";

                    }

                    description "Route tag.";

                }

                leaf Preference {

                    type base:Basetype_UnsignedChar {

                        range "1..255";

                    }

                    description "Route preference.";

                }

                leaf Description {

                    type base:Basetype_Text {

                        length "1..60";

                    }

                    description "Description information.";

                }

                leaf Permanent {

                    type base:Basetype_Boolean;

                    description "Permanent attribute of route.";

                }

                container BackupPathAttribute {

                    description "Backup path attribute.";

                    leaf BackupIfIndex {

                        type base:Basetype_NameAndIndexUnion;

                        description "Backup interface index.";

                    }

                    leaf BackupNexthopIpv4Address {

                        type base:Basetype_Ipv4Address;

                        description "Backup nexthop IPv4 address.";

                    }

                }

                container BfdAttribute {

                    description "BFD attribute.";

                    leaf BfdWorkMode {

                        type enumeration {

                            enum 1;

                            enum 2;

                        }

                        description "BFD work mode.

                                1: Control-packet mode.

                                2: Echo-packet mode.";

                    }

                    leaf BfdSourceIpv4Address {

                        type base:Basetype_Ipv4Address;

                        description "BFD source IPv4 address.";

                    }

                }

                leaf TrackEntryID {

                    type base:Basetype_UnsignedInteger32 {

                        range "1..1024";

                    }

                    description "Track Entry ID.";

                }

                leaf LdpSync {

                    type base:Basetype_Boolean;

                    description "LdpSync attribute of route.";

                }

            }

        }

        container Ipv6StaticRouteConfigurations {

            description "IPv6 static route running information.

                This table supports creating rows.";

            list RouteEntry {

                description "Row name of Ipv6StaticRouteConfigurations table.";

                key "DestVrfIndex DestTopologyIndex Ipv6Address Ipv6PrefixLength NexthopVrfIndex NexthopIpv6Address IfIndex";

                leaf DestVrfIndex {

                    type union {

                        type base:Basetype_EmptyString;

                        type base:Basetype_NameAndIndexUnion;

                    }

                    description "Destination VRF index.";

                }

                leaf DestTopologyIndex {

                    type base:Basetype_UnsignedInteger32;

                    description "Destination topology index.";

                }

                leaf Ipv6Address {

                    type base:Basetype_Ipv6Address;

                    description "Destination IPv6 address.";

                }

                leaf Ipv6PrefixLength {

                    type base:Basetype_UnsignedChar {

                        range "0..128";

                    }

                    description "Length of the destination IPv6 address prefix.";

                }

                leaf NexthopVrfIndex {

                    type union {

                        type base:Basetype_EmptyString;

                        type base:Basetype_NameAndIndexUnion;

                    }

                    description "Nexthop VRF index.";

                }

                leaf NexthopIpv6Address {

                    type base:Basetype_Ipv6Address;

                    description "Nexthop IPv6 address.";

                }

                leaf IfIndex {

                    type union {

                        type base:Basetype_EmptyString;

                        type base:Basetype_NameAndIndexUnion;

                    }

                    description "Out interface index.";

                }

                leaf Tag {

                    type base:Basetype_UnsignedInteger32 {

                        range "0..4294967295";

                    }

                    description "Route tag.";

                }

                leaf Preference {

                    type base:Basetype_UnsignedChar {

                        range "1..255";

                    }

                    description "Route preference.";

                }

                leaf Description {

                    type base:Basetype_Text {

                        length "1..60";

                    }

                    description "Description information.";

                }

                leaf Permanent {

                    type base:Basetype_Boolean;

                    description "Permanent attribute of route.";

                }

                container BfdAttribute {

                    description "BFD attribute.";

                    leaf BfdWorkMode {

                        type enumeration {

                            enum 1;

                            enum 2;

                        }

                        description "BFD work mode.

                                1: Control-packet mode.

                                2: Echo-packet mode.";

                    }

                    leaf BfdSourceIpv6Address {

                        type base:Basetype_Ipv6Address;

                        description "BFD source IPv6 address.";

                    }

                }

            }

        }

        container Ipv4Group {

            description "IPv4 group running information.

                This table supports creating rows.";

            list GroupEntry {

                description "Row name of Ipv4Group table.";

                key "Group";

                leaf Group {

                    type base:Basetype_String {

                        length "1..31";

                    }

                    description "Group name.";

                }

            }

        }

        container Ipv4GroupPrefix {

            description "IPv4 group prefix running information.

                This table supports creating rows.";

            list GroupPrefixEntry {

                description "Row name of Ipv4GroupPrefix table.";

                key "Group Ipv4Address Ipv4PrefixLength";

                leaf Group {

                    type base:Basetype_String {

                        length "1..31";

                    }

                    description "Group name.";

                }

                leaf Ipv4Address {

                    type base:Basetype_Ipv4Address;

                    description "Destination IPv4 address.";

                }

                leaf Ipv4PrefixLength {

                    type base:Basetype_UnsignedChar {

                        range "0..32";

                    }

                    description "Length of the destination IPv4 address prefix.";

                }

            }

        }

        container Ipv4StaticRouteGroup {

            description "IPv4 static route group running information.

                This table supports creating rows.";

            list RouteGroupEntry {

                description "Row name of Ipv4StaticRouteGroup table.";

                key "DestVrfIndex DestTopologyIndex Group NexthopVrfIndex NexthopIpv4Address IfIndex";

                leaf DestVrfIndex {

                    type union {

                        type base:Basetype_EmptyString;

                        type base:Basetype_NameAndIndexUnion;

                    }

                    description "Destination VRF index.";

                }

                leaf DestTopologyIndex {

                    type base:Basetype_UnsignedInteger32;

                    description "Destination topology index.";

                }

                leaf Group {

                    type base:Basetype_String {

                        length "1..31";

                    }

                    description "Group name.";

                }

                leaf NexthopVrfIndex {

                    type union {

                        type base:Basetype_EmptyString;

                        type base:Basetype_NameAndIndexUnion;

                    }

                    description "Nexthop VRF index.";

                }

                leaf NexthopIpv4Address {

                    type base:Basetype_Ipv4Address;

                    description "Nexthop IPv4 address.";

                }

                leaf IfIndex {

                    type union {

                        type base:Basetype_EmptyString;

                        type base:Basetype_NameAndIndexUnion;

                    }

                    description "Out interface index.";

                }

                leaf Tag {

                    type base:Basetype_UnsignedInteger32 {

                        range "0..4294967295";

                    }

                    description "Route tag.";

                }

                leaf Preference {

                    type base:Basetype_UnsignedChar {

                        range "1..255";

                    }

                    description "Route preference.";

                }

                leaf Description {

                    type base:Basetype_Text {

                        length "1..60";

                    }

                    description "Description information.";

                }

                leaf Permanent {

                    type base:Basetype_Boolean;

                    description "Permanent attribute of route.";

                }

                container BackupPathAttribute {

                    description "Backup path attribute.";

                    leaf BackupIfIndex {

                        type base:Basetype_NameAndIndexUnion;

                        description "Backup interface index.";

                    }

                    leaf BackupNexthopIpv4Address {

                        type base:Basetype_Ipv4Address;

                        description "Backup nexthop IPv4 address.";

                    }

                }

                container BfdAttribute {

                    description "BFD attribute.";

                    leaf BfdWorkMode {

                        type enumeration {

                            enum 1;

                            enum 2;

                        }

                        description "BFD work mode.

                                1: Control-packet mode.

                                2: Echo-packet mode.";

                    }

                    leaf BfdSourceIpv4Address {

                        type base:Basetype_Ipv4Address;

                        description "BFD source IPv4 address.";

                    }

                }

                leaf TrackEntryID {

                    type base:Basetype_UnsignedInteger32 {

                        range "1..1024";

                    }

                    description "Track Entry ID.";

                }

                leaf LdpSync {

                    type base:Basetype_Boolean;

                    description "LdpSync attribute of route.";

                }

            }

        }

        container Ipv4GuardRouteConfigurations {

            description "IPv4 static route configuration information.

                This table supports creating rows.";

            list RouteEntry {

                description "Row name of Ipv4StaticRouteConfigurations table.";

                key "Ipv4Address Ipv4PrefixLength";

                leaf Ipv4Address {

                    type base:Basetype_Ipv4Address;

                    description "Destination IPv4 address.";

                }

                leaf Ipv4PrefixLength {

                    type base:Basetype_UnsignedChar {

                        range "0..32";

                    }

                    description "Length of the destination IPv4 address prefix.";

                }

            }

        }

        container Ipv6GuardRouteConfigurations {

            description "IPv6 static route configuration information.

                This table supports creating rows.";

            list RouteEntry {

                description "Row name of Ipv6StaticRouteConfigurations table.";

                key "Ipv6Address Ipv6PrefixLength";

                leaf Ipv6Address {

                    type base:Basetype_Ipv6Address;

                    description "Destination IPv6 address.";

                }

                leaf Ipv6PrefixLength {

                    type base:Basetype_UnsignedChar {

                        range "0..128";

                    }

                    description "Length of the destination IPv6 address prefix.";

                }

            }

        }

    }

}
