module H3C-routepolicy-data {

    namespace "http://www.h3c.com/netconf/data:1.0";

    prefix "routepolicy-data";

    import comware-basetype {

         prefix "base";

    }

    import comware-extension {

         prefix "ext";

    }

    organization "NEW H3C Technologies Co., Ltd.";

    contact "Website: http://www.h3c.com";

    description "The module entities for routepolicy data.";

    revision 2020-04-10 {

        description "Synchronize the modification of the schema file to the YANG file.";

    }

    revision 2020-01-06 {

        description "Initial revision.";

    }

    container RoutePolicy {

        config false;

        container IPv4PrefixList {

            description "IPv4 prefix list running information.

                This table supports creating rows.";

            list PrefixList {

                description "Row name of IPv4 prefix list Table";

                key "PrefixListName Index";

                leaf PrefixListName {

                    type base:Basetype_String {

                        length "1..63";

                    }

                    description "IPv4 prefix list name, a case-sensitive string of 1 to 63 characters.";

                }

                leaf Index {

                    type base:Basetype_UnsignedInteger32 {

                        range "1..65535";

                    }

                    description "Index";

                }

                leaf Mode {

                    type base:Basetype_UnsignedInteger32 {

                        range "0..1";

                    }

                    description "Mode(0: permint, 1: deny)";

                }

                leaf Ipv4Address {

                    type base:Basetype_Ipv4Address;

                    description "Ipv4Address";

                }

                leaf Ipv4PrefixLength {

                    type base:Basetype_UnsignedInteger32 {

                        range "0..32";

                    }

                    description "Ipv4PrefixLength";

                }

                leaf MinPrefixLength {

                    type base:Basetype_UnsignedInteger32 {

                        range "0..32";

                    }

                    description "MinPrefixLength";

                }

                leaf MaxPrefixLength {

                    type base:Basetype_UnsignedInteger32 {

                        range "0..32";

                    }

                    description "MaxPrefixLength";

                }

            }

        }

        container IPv6PrefixList {

            description "IPv6 prefix list running information.

                This table supports creating rows.";

            list PrefixList {

                description "Row name of IPv6 prefix list Table";

                key "PrefixListName Index";

                leaf PrefixListName {

                    type base:Basetype_String {

                        length "1..63";

                    }

                    description "IPv6 prefix list name, a case-sensitive string of 1 to 63 characters.";

                }

                leaf Index {

                    type base:Basetype_UnsignedInteger32 {

                        range "1..65535";

                    }

                    description "Index";

                }

                leaf Mode {

                    type base:Basetype_UnsignedInteger32 {

                        range "0..1";

                    }

                    description "Mode(0: permint, 1: deny)";

                }

                leaf Ipv6Address {

                    type base:Basetype_Ipv6Address;

                    description "Ipv6Address";

                }

                leaf Ipv6PrefixLength {

                    type base:Basetype_UnsignedInteger32 {

                        range "0..128";

                    }

                    description "Ipv6PrefixLength";

                }

                leaf MinPrefixLength {

                    type base:Basetype_UnsignedInteger32 {

                        range "0..128";

                    }

                    description "MinPrefixLength";

                }

                leaf MaxPrefixLength {

                    type base:Basetype_UnsignedInteger32 {

                        range "0..128";

                    }

                    description "MaxPrefixLength";

                }

            }

        }

        container Policy {

            description "Policy running information.

                This table supports creating rows.";

            list Entry {

                description "Row name of Policy Table";

                key "PolicyName Index";

                leaf PolicyName {

                    type base:Basetype_String {

                        length "1..63";

                    }

                    description "Policy name, a case-sensitive string of 1 to 63 characters.";

                }

                leaf Index {

                    type base:Basetype_UnsignedInteger32 {

                        range "0..65535";

                    }

                    description "Index";

                }

                leaf Mode {

                    type base:Basetype_UnsignedInteger32 {

                        range "0..1";

                    }

                    description "Mode(0: permint, 1: deny)";

                }

                leaf Description {

                    type base:Basetype_String {

                        length "1..80";

                    }

                    description "Description of Route Policy";

                }

                container Match {

                    description "Match";

                    leaf IPv4AddressPrefixList {

                        type base:Basetype_String {

                            length "1..63";

                        }

                        description "IPv4 prefix list name, a case-sensitive string of 1 to 63 characters.";

                    }

                    leaf IPv6AddressPrefixList {

                        type base:Basetype_String {

                            length "1..63";

                        }

                        description "IPv6 prefix list name, a case-sensitive string of 1 to 63 characters.";

                    }

                    leaf-list ExtcommunityList {

                        type base:Basetype_UnsignedInteger32 {

                            range "1..65535";

                        }

                        description "a specified extended community list";

                    }

                    leaf Tag {

                        type base:Basetype_UnsignedInteger32 {

                            range "0..4294967295";

                        }

                        description "IGP routes have the specified Tag";

                    }

                    leaf-list Interface {

                        type base:Basetype_NameAndIndexUnion;

                        description "Interface index.";

                    }

                    leaf-list RouteType {

                        type base:Basetype_UnsignedInteger32 {

                            range "1..14";

                        }

                        description "Route type.";

                    }

                    leaf TagList {

                        type base:Basetype_UnsignedInteger32 {

                            range "1..65535";

                        }

                        description "IGP routes have the specified TagList";

                    }

                    leaf RdList {

                        type base:Basetype_UnsignedInteger32 {

                            range "1..65535";

                        }

                        description "if-match rd-list number.";

                    }

                }

                list MatchCommunityList {

                    description "MatchCommunityList";

                    key "List WholeMatch";

                    leaf List {

                        type base:Basetype_String {

                            length "1..63";

                        }

                        description "CommunityList name, a case-sensitive string of 1 to 63 characters.";

                    }

                    leaf WholeMatch {

                        type base:Basetype_UnsignedInteger32 {

                            range "0..1";

                        }

                        description "Match all communities exactly.";

                    }

                }

                container Apply {

                    description "Apply action.";

                    leaf-list ExtCommunityRtValue {

                        type base:Basetype_String {

                            length "3..21";

                        }

                        description "The value of Ext Community Route target(RT).";

                        ext:support-incremental "true";

                    }

                    leaf ExtCommunityRtType {

                        type base:Basetype_UnsignedInteger32 {

                            range "1..2";

                        }

                        description "The Ext Community Rt additive type.";

                    }

                    leaf VpnPeerId {

                        type base:Basetype_UnsignedInteger32 {

                            range "1..134217727";

                        }

                        description "Set vpn-peer-id.";

                    }

                    leaf CostValue {

                        type base:Basetype_UnsignedInteger32 {

                            range "0..4294967295";

                        }

                        description "Route cost value.";

                    }

                    leaf CostMode {

                        type base:Basetype_UnsignedInteger32 {

                            range "0..2";

                        }

                        description "Route cost change mode.";

                    }

                    leaf LocalPreference {

                        type base:Basetype_UnsignedInteger32 {

                            range "0..4294967295";

                        }

                        description "BGP route local preference.";

                    }

                    leaf-list ASPath {

                        type base:Basetype_UnsignedInteger32 {

                            range "1..4294967295";

                        }

                        description "AS path value.";

                    }

                    leaf ASPathType {

                        type base:Basetype_UnsignedInteger32 {

                            range "1..2";

                        }

                        description "AS path additive type.";

                    }

                    leaf-list CommunityNumber {

                        type base:Basetype_String {

                            length "1..11";

                        }

                        description "Community number.";

                    }

                    leaf-list CommunityAttr {

                        type base:Basetype_UnsignedInteger32 {

                            range "1..4";

                        }

                        description "Community attribution.";

                    }

                    leaf CommunityType {

                        type base:Basetype_UnsignedInteger32 {

                            range "0..2";

                        }

                        description "Community type.";

                    }

                    leaf PreferredValue {

                        type base:Basetype_UnsignedInteger32 {

                            range "0..65535";

                        }

                        description "Specify a preferred value for BGP routes.";

                    }

                    leaf Exp {

                        type base:Basetype_UnsignedInteger32 {

                            range "0..7";

                        }

                        description "Set Exp.";

                    }

                }

                container ApplyIpv4NextHop {

                    description "Specify next hop.";

                    leaf NextHopAddr {

                        type base:Basetype_Ipv4Address;

                        description "Specify next hop address, x.x.x.x Ip-address.";

                    }

                    leaf Public {

                        type enumeration {

                            enum 0;

                            enum 1;

                        }

                        description "Public network (0: not configured, 1: configured).";

                    }

                    leaf VrfName {

                        type base:Basetype_String {

                            length "0..31";

                        }

                        description "Vpn instance name.";

                    }

                }

                leaf Continue {

                    type base:Basetype_UnsignedInteger32 {

                        range "0..65535";

                    }

                    description "Set the next node to be matched.";

                }

            }

        }

        container ExtcommunityList {

            description "a specified extended community list.

                This table supports creating rows.";

            list List {

                description "Row name of ExtcommunityList Table.";

                key "ListNum Index";

                leaf ListNum {

                    type base:Basetype_UnsignedInteger32 {

                        range "1..65535";

                    }

                    description "List Number.";

                }

                leaf Index {

                    type base:Basetype_UnsignedInteger32 {

                        range "1..4294967295";

                    }

                    description "Index Number.";

                }

                leaf Mode {

                    type base:Basetype_UnsignedInteger32 {

                        range "0..1";

                    }

                    description "Mode(0: permint, 1: deny)";

                }

                leaf-list Rt {

                    type base:Basetype_String {

                        length "3..21";

                    }

                    description "route-target.";

                }

                leaf-list SoO {

                    type base:Basetype_String {

                        length "3..21";

                    }

                    description "site-of-origin.";

                }

            }

        }

        container CommunityList {

            description "a specified community list.

                This table supports creating rows.";

            list List {

                description "Row name of CommunityList Table.";

                key "ListName Level Index";

                leaf ListName {

                    type base:Basetype_String {

                        length "1..63";

                    }

                    description "List Name.";

                }

                leaf Level {

                    type base:Basetype_UnsignedInteger32 {

                        range "1..2";

                    }

                    description "List level.";

                }

                leaf Index {

                    type base:Basetype_UnsignedInteger32 {

                        range "1..4294967295";

                    }

                    description "Node.";

                }

                leaf Mode {

                    type base:Basetype_UnsignedInteger32 {

                        range "0..1";

                    }

                    description "Mode(0: permint, 1: deny)";

                }

                leaf-list CommunityNumber {

                    type base:Basetype_String {

                        length "1..11";

                    }

                    description "Community number.";

                }

                leaf-list CommunityAttr {

                    type base:Basetype_UnsignedInteger32 {

                        range "1..4";

                    }

                    description "Community attribution.";

                }

                leaf RegularExpression {

                    type base:Basetype_String {

                        length "1..63";

                    }

                    description "Regular expression.";

                }

            }

        }

        container TagList {

            description "a specified tag list.

                This table supports creating rows.";

            list List {

                description "Row name of TagList Table.";

                key "ListNum Index";

                leaf ListNum {

                    type base:Basetype_UnsignedInteger32 {

                        range "1..65535";

                    }

                    description "List Number.";

                }

                leaf Index {

                    type base:Basetype_UnsignedInteger32 {

                        range "1..4294967295";

                    }

                    description "Index Number.";

                }

                leaf Mode {

                    type base:Basetype_UnsignedInteger32 {

                        range "0..1";

                    }

                    description "Mode(0: permint, 1: deny)";

                }

                leaf-list TagValue {

                    type base:Basetype_UnsignedInteger32 {

                        range "0..4294967295";

                    }

                    description "Tag Value.";

                }

            }

        }

        container RdList {

            description "ip rd-list configuration information.

                This table supports creating rows.";

            list List {

                description "Row name of RdList Table";

                key "ListNum Index";

                leaf ListNum {

                    type base:Basetype_UnsignedInteger32 {

                        range "1..65535";

                    }

                    description "rd-list number.";

                }

                leaf Index {

                    type base:Basetype_UnsignedInteger32 {

                        range "1..4294967295";

                    }

                    description "Index number";

                }

                leaf Mode {

                    type base:Basetype_UnsignedInteger32 {

                        range "0..1";

                    }

                    description "Mode(0: permint, 1: deny)";

                }

                leaf-list RdValue {

                    type base:Basetype_String {

                        length "3..21";

                    }

                    description "route-distinguisher,a case-sensitive string 0f 3 to 21 characters.";

                }

            }

        }

    }

}
