module H3C-ikev2-data {

    namespace "http://www.h3c.com/netconf/data:1.0";

    prefix "ikev2-data";

    import comware-basetype {

         prefix "base";

    }

    import comware-extension {

         prefix "ext";

    }

    organization "NEW H3C Technologies Co., Ltd.";

    contact "Website: http://www.h3c.com";

    description "The module entities for ikev2 data.";

    revision 2019-12-07 {

        description "Initial revision.";

    }

    container IKEv2 {

        config false;

        container GlobalConf {

            description "IKEv2 global configuration";

            container DPD {

                description "Dead Peer Detection(DPD) parameters, Members include: Mode, Interval, Retry";

                leaf Mode {

                    type enumeration {

                        enum 1;

                        enum 2;

                    }

                    description "Enumeration

                          1-On-demand

                          2-Periodic";

                }

                leaf Interval {

                    type base:Basetype_UnsignedInteger32 {

                        range "10..3600";

                    }

                    description "Interval time of triggering DPD";

                }

                leaf Retry {

                    type base:Basetype_UnsignedInteger32 {

                        range "2..60";

                    }

                    description "The DPD retry interval";

                }

            }

            leaf CookieChallenge {

                type base:Basetype_UnsignedInteger32 {

                    range "0..65535";

                }

                description "CookieChallenge";

            }

            leaf NatKeepaliveInterval {

                type base:Basetype_UnsignedInteger32 {

                    range "5..3600";

                }

                description "NAT keepalive Interval";

            }

        }

        container Profiles {

            description "Name of IKEv2 profile

                This table supports creating rows.";

            list Profile {

                description "Row name";

                key "Name";

                leaf Name {

                    type base:Basetype_NameString {

                        length "1..63";

                    }

                    description "Name of IKE profile, String, Length: 1 to 63 characters Case insensitive";

                }

                leaf Priority {

                    type base:Basetype_UnsignedInteger32;

                    description "The priority of IKEv2 profile, Unsigned integer, Value range: 1 to 65535, The more small value the more high priority";

                }

                leaf LocalAuthMethod {

                    type base:Basetype_UnsignedInteger32;

                    description "LocalAuthMethod Enumeration:

                           1—Pre-Shared-Key 

                           2—RSA-Signature 

                           3—DSA-Signature

                           4—ECDSA-Signature";

                }

                container RemoteAuthMethodList {

                    description "Remote identity authentication method";

                    leaf-list RemoteAuthMethodItem {

                        type base:Basetype_UnsignedInteger32;

                        description "Remote identity authentication method";

                    }

                }

                container ConfigExchangeList {

                    description "Configuration exchange";

                    leaf-list ConfigExchangeItem {

                        type base:Basetype_UnsignedInteger32;

                        description "Enable configuration exchange";

                    }

                }

                leaf Keychain {

                    type base:Basetype_NameString {

                        length "1..63";

                    }

                    description "Reference an IKE keychain for the IKEv2 profile";

                }

                leaf SADuration {

                    type base:Basetype_UnsignedInteger32;

                    description "IKEv2 SA life time";

                }

                leaf NatKeepaliveInterval {

                    type base:Basetype_UnsignedInteger32;

                    description "NAT keepalive interval for the IKEv2 profile";

                }

                leaf InsideVRF {

                    type base:Basetype_NameString {

                        length "1..31";

                    }

                    description "Inside VPN instance";

                }

                container DPD {

                    description "Dead Peer Detection(DPD) parameters, Data structureMembers include: Mode, Interval, Retry";

                    leaf Mode {

                        type base:Basetype_UnsignedInteger32;

                        description "The mode of DPD

                                Enumeration:

                                1-On-demand

                                2-Periodic";

                    }

                    leaf Interval {

                        type base:Basetype_UnsignedInteger32;

                        description "Interval time of triggering DPD, Unsigned integer, Value range: 1 to 3600, in seconds";

                    }

                    leaf Retry {

                        type base:Basetype_UnsignedInteger32;

                        description "The DPD retry interval, Unsigned integer, Value range:2 to 60, in seconds. Default value is 5";

                    }

                }

                container MatchVRF {

                    description "VPN instance for the IKEv2 profile";

                    leaf MatchVrfType {

                        type base:Basetype_UnsignedInteger32;

                        description "The type of the identity

                                Enumeration:

                                1-any,

                                2-vrf name";

                    }

                    leaf VRFName {

                        type base:Basetype_NameString {

                            length "1..31";

                        }

                        description "Inside VPN instance";

                    }

                }

                container AAAAuthorization {

                    leaf Domain {

                        type base:Basetype_NameString {

                            length "1..255";

                        }

                    }

                    leaf UserName {

                        type base:Basetype_NameString {

                            length "1..55";

                        }

                    }

                }

                container IdentityLocal {

                    description "Identity information for the IKEv2 profile,Members include:IdentityType,StringValue or IpAddress";

                    leaf IdentityType {

                        type base:Basetype_UnsignedInteger32;

                        description "Enable configuration exchange

                                1-Ipv4Address

                                2-Ipv6Address

                                3-dn

                                4-email

                                5-fqdn

                                6-key-id";

                    }

                    leaf StringValue {

                        type base:Basetype_NameString;

                        description "Identity Value, String, Length: 1 to 255 characters Case insensitive";

                    }

                    leaf IpAddress {

                        type base:Basetype_IpAddress;

                        description "The value of address, it is whether IPv4 address or IPv6 address lies on the AddressType";

                    }

                }

            }

        }

        container MatchRemoteIpv4Address {

            description "Match remote identity IPv4 address information

                This table supports creating rows.";

            list RemoteID {

                description "Row name";

                key "Profile Ipv4Address Ipv4Mask";

                leaf Profile {

                    type base:Basetype_NameString {

                        length "1..63";

                    }

                    description "Name of IKEv2 profile, String, Length: 1 to 63 characters Case insensitive";

                }

                leaf Ipv4Address {

                    type base:Basetype_Ipv4Address;

                    description "The value of IPv4 address";

                }

                leaf Ipv4Mask {

                    type base:Basetype_Ipv4Address;

                    description "The mask of IPv4 address";

                }

            }

        }

        container MatchRemoteIpv6Address {

            description "Match remote identity IPv6 address information

                This table supports creating rows.";

            list RemoteID {

                description "Row name";

                key "Profile Ipv6Address Ipv6PrefixLength";

                leaf Profile {

                    type base:Basetype_NameString {

                        length "1..63";

                    }

                    description "Name of IKEv2 profile, String, Length: 1 to 63 characters Case insensitive";

                }

                leaf Ipv6Address {

                    type base:Basetype_Ipv6Address;

                    description "The value of IPv6 address";

                }

                leaf Ipv6PrefixLength {

                    type base:Basetype_UnsignedInteger32 {

                        range "0..128";

                    }

                    description "The prefix length of IPv6 address";

                }

            }

        }

        container MatchRemoteIpv4Range {

            description "Match remote identity IPv4 range information

                This table supports creating rows.";

            list RemoteID {

                description "Row name";

                key "Profile BeginIpv4Address EndIpv4Address";

                leaf Profile {

                    type base:Basetype_NameString {

                        length "1..63";

                    }

                    description "Name of IKEv2 profile, String, Length: 1 to 63 characters Case insensitive";

                }

                leaf BeginIpv4Address {

                    type base:Basetype_Ipv4Address;

                    description "Start IPv4 Address";

                }

                leaf EndIpv4Address {

                    type base:Basetype_Ipv4Address;

                    description "End IPv4 Address";

                }

            }

        }

        container MatchRemoteIpv6Range {

            description "Match remote identity IPv6 range information

                This table supports creating rows.";

            list RemoteID {

                description "Row name";

                key "Profile BeginIpv6Address EndIpv6Address";

                leaf Profile {

                    type base:Basetype_NameString {

                        length "1..63";

                    }

                    description "Name of IKEv2 profile, String, Length: 1 to 63 characters Case insensitive";

                }

                leaf BeginIpv6Address {

                    type base:Basetype_Ipv6Address;

                    description "Start IPv6 Address";

                }

                leaf EndIpv6Address {

                    type base:Basetype_Ipv6Address;

                    description "End IPv6 Address";

                }

            }

        }

        container ProfileMatchRemotePeer {

            description "The rule about how to match remote identity when it's peer

                This table supports creating rows.";

            list MatchRemotePeer {

                description "Row name";

                key "Profile PeerType PeerName";

                leaf Profile {

                    type base:Basetype_NameString {

                        length "1..63";

                    }

                    description "Name of IKEv2 profile, String, Length: 1 to 63 characters Case insensitive";

                }

                leaf PeerType {

                    type enumeration {

                        enum 1;

                        enum 2;

                        enum 3;

                    }

                    description "Peer Type, Enumeration:

                          1-fqdn

                          2-email

                          3-key-id";

                }

                leaf PeerName {

                    type base:Basetype_NameString {

                        length "1..255";

                    }

                    description "The peer name, String, Length:1 to 255 charactersCase sensitive.";

                }

            }

        }

        container ProfileMatchLocalIpAddress {

            description "Profile Match Local IPv4 or IPv6 address information

                This table supports creating rows.";

            list MatchLocalIpAddress {

                description "Row name";

                key "Profile IPType Address";

                leaf Profile {

                    type base:Basetype_NameString {

                        length "1..63";

                    }

                    description "Name of IKEv2 profile, String, Length: 1 to 63 characters, case insensitive";

                }

                leaf IPType {

                    type enumeration {

                        enum 1;

                        enum 2;

                    }

                    description "Enumeration:

                          1—Ipv4Address

                          2—Ipv6Address";

                }

                leaf Address {

                    type base:Basetype_IpAddress;

                    description "The value of address, it is whether IPv4 address or IPv6 address lies on the AddressType";

                }

            }

        }

        container ProfileMatchLocalInterfaces {

            description "Profile Match Local Interface information

                This table supports creating rows.";

            list MatchLocalInterface {

                description "Row name";

                key "Profile IfIndex";

                leaf Profile {

                    type base:Basetype_NameString {

                        length "1..63";

                    }

                    description "Name of IKEv2 profile, String, Length: 1 to 63 characters, case insensitive";

                }

                leaf IfIndex {

                    type base:Basetype_UnsignedInteger32;

                    description "";

                }

            }

        }

        container Policies {

            description "Name of IKEV2 Policies

                This table supports creating rows.";

            list Policy {

                description "Row name";

                key "Name";

                leaf Name {

                    type base:Basetype_NameString {

                        length "1..63";

                    }

                    description "Name of IKEV2 Policy, String, Length: 1 to 63 characters Case insensitive";

                }

                leaf Priority {

                    type base:Basetype_UnsignedInteger32 {

                        range "1..65535";

                    }

                    description "The priority of IKEV2 Policy, Unsigned integer, Value range: 1 to 65535, The more small value the more high priority";

                }

                container ProposalList {

                    description "Reference an IKEV2 proposal for the IKEV2 Policy, Members include: ProposalItem";

                    leaf-list ProposalItem {

                        type base:Basetype_NameString {

                            length "1..63";

                        }

                        description "Name of IKEV2 Proposal, String, Length: 1 to 63 characters Case insensitive";

                    }

                }

                container MatchVRF {

                    description "VPN instance for the IKEv2 policy,Members include: MatchVRFType,VRFName";

                    leaf MatchVRFType {

                        type enumeration {

                            enum 0;

                            enum 1;

                            enum 2;

                        }

                        description "VPN instance type

                                Enumeration:

                                0-Public

                                1-any

                                2-vrf name";

                    }

                    leaf VRFName {

                        type base:Basetype_NameString {

                            length "1..31";

                        }

                        description "VRF name, String, Length: 1 to 31 characters Case insensitive";

                    }

                }

            }

        }

        container PolicyMatchLocalIpAddress {

            description "Policy Match Local IPv4 or IPv6 address information

                This table supports creating rows.";

            list MatchLocalIpAddress {

                description "Row name";

                key "Policy IPType IpAddress";

                leaf Policy {

                    type base:Basetype_NameString {

                        length "1..63";

                    }

                    description "Name of IKEV2 policy, String, Length: 1 to 63 characters, case insensitive";

                }

                leaf IPType {

                    type enumeration {

                        enum 1;

                        enum 2;

                    }

                    description "Enumeration:

                          1—Ipv4Address

                          2—Ipv6Address";

                }

                leaf IpAddress {

                    type base:Basetype_IpAddress;

                    description "The value of address, it is whether IPv4 address or IPv6 address lies on the AddressType";

                }

            }

        }

        container PolicyMatchLocalInterfaces {

            description "Policy Match Local Interface information

                This table supports creating rows.";

            list MatchLocalInterface {

                description "Row name";

                key "Policy IfIndex";

                leaf Policy {

                    type base:Basetype_NameString {

                        length "1..63";

                    }

                    description "Name of IKEV2 policy, String, Length: 1 to 63 characters, case insensitive";

                }

                leaf IfIndex {

                    type base:Basetype_UnsignedInteger32;

                    description "";

                }

            }

        }

        container Proposals {

            description "Name of IKEv2 proposal

                This table supports creating rows.";

            list Proposal {

                description "Row name";

                key "Name";

                leaf Name {

                    type base:Basetype_NameString {

                        length "1..63";

                    }

                    description "Name of IKE proposal, String, Length: 1 to 63 characters Case insensitive";

                }

                container IntegrityList {

                    description "Integrity protection algorithm list";

                    leaf-list IntegrityItem {

                        type base:Basetype_UnsignedInteger32;

                        description "Integrity protection algorithm";

                    }

                }

                container EncryptionList {

                    description "Encryption algorithm list";

                    leaf-list EncryptionItem {

                        type base:Basetype_UnsignedInteger32;

                        description "Encryption algorithm";

                    }

                }

                container DhList {

                    description "DH group list";

                    leaf-list DhItem {

                        type base:Basetype_UnsignedInteger32;

                        description "DH group";

                    }

                }

                container PrfAlgList {

                    description "PRF algorithm list";

                    leaf-list PrfAlgItem {

                        type base:Basetype_UnsignedInteger32;

                        description "PRF algorithm";

                    }

                }

            }

        }

        container Keychains {

            description "IKEv2 Keychains configuration

                This table supports creating rows.";

            list Keychain {

                description "Row name";

                key "Name Peer";

                leaf Name {

                    type base:Basetype_NameString {

                        length "1..63";

                    }

                    description "IKEv2 Keychain name, 1 to 63 characters Case insensitive";

                }

                leaf Peer {

                    type base:Basetype_NameString {

                        length "1..63";

                    }

                    description "Peer Name, 1 to 63 characters Case insensitive";

                }

                leaf HostName {

                    type base:Basetype_NameString {

                        length "1..253";

                    }

                    description "HostName, 1 to 253 characters Case insensitive";

                }

                container Identity {

                    description "ID of an IKEv2 peer,  Members include: Type, IPAddress, Value";

                    leaf-list IdentityType {

                        type enumeration {

                            enum 1;

                            enum 2;

                            enum 3;

                            enum 4;

                            enum 5;

                        }

                        description "IdentityType, Enumeration:

                                  1-Ipv4Address

                                  2-Ipv6Address

                                  3-email

                                  4-fqdn

                                  5-key-id";

                    }

                    leaf-list StringValue {

                        type base:Basetype_OctectString255;

                        description "The value when the identity isn't IP address, String, Length: 0 to 255 charactersCase sensitive";

                    }

                    leaf-list LocalIpAddress {

                        type base:Basetype_IpAddress;

                        description "The value of address when the identity is IP address";

                    }

                }

                container Address {

                    description "Address of an IKEv2 peer,  Members include: AddressType, IPAddress, Ipv4Mask, Ipv6PrefixLength";

                    leaf-list AddressType {

                        type enumeration {

                            enum 1;

                            enum 2;

                        }

                        description "AddressType, Enumeration:

                                  1-Ipv4Address

                                  2-Ipv6Address";

                    }

                    leaf-list IpAddress {

                        type base:Basetype_IpAddress;

                        description "The value of address when the AddressType is IP address";

                    }

                    leaf-list Ipv4Mask {

                        type base:Basetype_Ipv4Address;

                        description "The mask of IPv4 address";

                    }

                    leaf-list Ipv6PrefixLength {

                        type base:Basetype_UnsignedInteger32 {

                            range "0..128";

                        }

                        description "The prefix length of IPv6 address, Unsigned integer, Value range: 0 to 128";

                    }

                }

                container PreSharedKeyLocal {

                    description "PreSharedKeyLocal";

                    leaf-list KeyType {

                        type enumeration {

                            enum 1;

                            enum 2;

                        }

                        description "The type of pre-shared key, Enumeration:

                                  1-Simple

                                  2-Cipher";

                    }

                    leaf-list Key {

                        type base:Basetype_NameString {

                            length "1..201";

                        }

                        description "According to the type of decision in length.

                                Plaintext key string

                                Length:1 to 128 characters

                                Or

                                Ciphertext key string

                                Length:1 to 201 characters";

                    }

                }

                container PreSharedKeyRemote {

                    description "PreSharedKeyRemote";

                    leaf-list KeyType {

                        type enumeration {

                            enum 1;

                            enum 2;

                        }

                        description "The type of pre-shared key, Enumeration:

                                  1-Simple

                                  2-Cipher";

                    }

                    leaf-list Key {

                        type base:Basetype_NameString {

                            length "1..201";

                        }

                        description "According to the type of decision in length.

                                Plaintext key string

                                Length:1 to 128 characters

                                Or

                                Ciphertext key string

                                Length:1 to 201 characters";

                    }

                }

                container PreSharedKeySymmetric {

                    description "PreSharedKeySymmetric";

                    leaf-list KeyType {

                        type enumeration {

                            enum 1;

                            enum 2;

                        }

                        description "The type of pre-shared key, Enumeration:

                                  1-Simple

                                  2-Cipher";

                    }

                    leaf-list Key {

                        type base:Basetype_NameString {

                            length "1..201";

                        }

                        description "According to the type of decision in length.

                                Plaintext key string

                                Length:1 to 128 characters

                                Or

                                Ciphertext key string

                                Length:1 to 201 characters";

                    }

                }

            }

        }

        container IKEv2Capabilities {

            description "IKEv2 support algorithm capabilities";

            list IKEv2Capability {

                description "Row name";

                key "AlgID";

                leaf AlgID {

                    type base:Basetype_UnsignedInteger32 {

                        range "1..max";

                    }

                    description "IKEv2 supports algorithm ID";

                }

                leaf AlgName {

                    type base:Basetype_String;

                    description "IKEv2 supports algorithm name";

                }

                leaf AlgType {

                    type base:Basetype_UnsignedInteger32;

                    description "Type of algorithm,Enumeration:

                            1-Diffie-Hellman group

                            2-Encryption algorithm

                            3-Prf algorithm";

                }

            }

        }

    }

}
