module H3C-radiusserver-data {

    namespace "http://www.h3c.com/netconf/data:1.0";

    prefix "radiusserver-data";

    import comware-basetype {

         prefix "base";

    }

    import comware-extension {

         prefix "ext";

    }

    organization "NEW H3C Technologies Co., Ltd.";

    contact "Website: http://www.h3c.com";

    description "The module entities for radiusserver data.";

    revision 2019-12-20 {

        description "Initial revision.";

    }

    container RadiusServer {

        config false;

        container Client {

            config false;

            container ClientInfos {

                list ClientInfo {

                    key "IpAddress VRF";

                    leaf IpAddress {

                        type base:Basetype_IpAddress;

                    }

                    leaf VRF {

                        type union {

                            type base:Basetype_EmptyString;

                            type base:Basetype_String {

                                length "0..31";

                            }

                        }

                    }

                }

            }

            container ActiveClients {

                list ActiveClient {

                    key "IpAddress VRF";

                    leaf IpAddress {

                        type base:Basetype_IpAddress;

                    }

                    leaf VRF {

                        type union {

                            type base:Basetype_EmptyString;

                            type base:Basetype_String {

                                length "0..31";

                            }

                        }

                    }

                }

            }

        }

        container Server {

            config false;

            container ActiveUsers {

                list ActiveUser {

                    key "Name";

                    leaf Name {

                        type base:Basetype_String {

                            length "1..55";

                        }

                    }

                    leaf Description {

                        type base:Basetype_String {

                            length "1..255";

                        }

                    }

                    container ValidityDateTime {

                        leaf EndValidityDateTime {

                            type base:Basetype_DateTime;

                        }

                    }

                    container AuthorizationInfo {

                        leaf AclNumber {

                            type base:Basetype_UnsignedInteger32 {

                                range "2000..5999";

                            }

                        }

                        leaf VLANID {

                            type base:Basetype_UnsignedInteger32 {

                                range "1..4094";

                            }

                        }

                    }

                }

            }

        }

    }

}
