module H3C-login-data {

    namespace "http://www.h3c.com/netconf/data:1.0";

    prefix "login-data";

    import comware-basetype {

         prefix "base";

    }

    import comware-extension {

         prefix "ext";

    }

    organization "NEW H3C Technologies Co., Ltd.";

    contact "Website: http://www.h3c.com";

    description "The module entities for login data.";

    revision 2019-12-20 {

        description "Initial revision.";

    }

    container Login {

        config false;

        container Class {

            config false;

            container Roles {

                list Role {

                    key "ClassType RoleName";

                    leaf ClassType {

                        type enumeration {

                            enum 1;

                            enum 2;

                            enum 3;

                            enum 4;

                        }

                    }

                    leaf RoleName {

                        type base:Basetype_String {

                            length "1..63";

                        }

                    }

                }

            }

            container Classes {

                list Class {

                    key "ClassType";

                    leaf ClassType {

                        type enumeration {

                            enum 1;

                            enum 2;

                            enum 3;

                            enum 4;

                        }

                    }

                    leaf AuthMode {

                        type enumeration {

                            enum 0;

                            enum 1;

                            enum 2;

                        }

                    }

                    leaf ProtocolIn {

                        type enumeration {

                            enum 0;

                            enum 1;

                            enum 2;

                            enum 5;

                        }

                    }

                }

            }

        }

        container Line {

            config false;

            container Lines {

                list Line {

                    key "LineType LineNumber";

                    leaf LineType {

                        type enumeration {

                            enum 1;

                            enum 2;

                            enum 3;

                            enum 4;

                        }

                    }

                    leaf LineNumber {

                        type base:Basetype_OctectString {

                            pattern "([0-9][0-9]*([/][0-9][0-9]*)*)";

                            length "1..10";

                        }

                    }

                    leaf AuthMode {

                        type enumeration {

                            enum 0;

                            enum 1;

                            enum 2;

                        }

                    }

                    leaf ProtocolIn {

                        type enumeration {

                            enum 0;

                            enum 1;

                            enum 2;

                            enum 5;

                        }

                    }

                }

            }

            container Roles {

                list Role {

                    key "LineType LineNumber RoleName";

                    leaf LineType {

                        type enumeration {

                            enum 1;

                            enum 2;

                            enum 3;

                            enum 4;

                        }

                    }

                    leaf LineNumber {

                        type base:Basetype_OctectString {

                            pattern "([0-9][0-9]*([/][0-9][0-9]*)*)";

                            length "1..10";

                        }

                    }

                    leaf RoleName {

                        type base:Basetype_String {

                            length "1..63";

                        }

                    }

                }

            }

        }

        container Header {

            leaf Incoming {

                type base:Basetype_OctectString {

                    pattern "[^	]*";

                    length "2..2002";

                }

            }

            leaf Legal {

                type base:Basetype_OctectString {

                    pattern "[^	]*";

                    length "2..2002";

                }

            }

            leaf Login {

                type base:Basetype_OctectString {

                    pattern "[^	]*";

                    length "2..2002";

                }

            }

            leaf Motd {

                type base:Basetype_OctectString {

                    pattern "[^	]*";

                    length "2..2002";

                }

            }

            leaf Shell {

                type base:Basetype_OctectString {

                    pattern "[^	]*";

                    length "2..2002";

                }

            }

        }

        container Specification {

            container AuthMode {

                leaf NoneAuth {

                    type base:Basetype_Boolean;

                }

                leaf PasswordAuth {

                    type base:Basetype_Boolean;

                }

            }

            container ProtocolIn {

                leaf Telnet {

                    type base:Basetype_Boolean;

                }

                leaf Pad {

                    type base:Basetype_Boolean;

                }

            }

        }

    }

}
