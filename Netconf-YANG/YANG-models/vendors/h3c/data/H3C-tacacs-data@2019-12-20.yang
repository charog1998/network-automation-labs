module H3C-tacacs-data {

    namespace "http://www.h3c.com/netconf/data:1.0";

    prefix "tacacs-data";

    import comware-basetype {

         prefix "base";

    }

    import comware-extension {

         prefix "ext";

    }

    organization "NEW H3C Technologies Co., Ltd.";

    contact "Website: http://www.h3c.com";

    description "The module entities for tacacs data.";

    revision 2019-12-20 {

        description "Initial revision.";

    }

    container Tacacs {

        config false;

        container Statistic {

            config false;

            container AuthServers {

                list AuthServer {

                    key "VRF IpType Host Port";

                    leaf VRF {

                        type union {

                            type base:Basetype_EmptyString;

                            type base:Basetype_String {

                                length "1..31";

                            }

                        }

                    }

                    leaf IpType {

                        type enumeration {

                            enum 0;

                            enum 1;

                            enum 2;

                        }

                    }

                    leaf Host {

                        type base:Basetype_IpAddress;

                    }

                    leaf Port {

                        type base:Basetype_UnsignedInteger32 {

                            range "1..65535";

                        }

                    }

                    leaf LastRoundTripTime {

                        type base:Basetype_UnsignedInteger32;

                    }

                    leaf PendingRequest {

                        type base:Basetype_UnsignedInteger32;

                    }

                    leaf Timeout {

                        type base:Basetype_UnsignedInteger32;

                    }

                    leaf Request {

                        type base:Basetype_UnsignedInteger32;

                    }

                    leaf ReqLogin {

                        type base:Basetype_UnsignedInteger32;

                    }

                    leaf ReqChangePass {

                        type base:Basetype_UnsignedInteger32;

                    }

                    leaf ReqSendPass {

                        type base:Basetype_UnsignedInteger32;

                    }

                    leaf ReqSendAuth {

                        type base:Basetype_UnsignedInteger32;

                    }

                    leaf Continue {

                        type base:Basetype_UnsignedInteger32;

                    }

                    leaf ContinueAbort {

                        type base:Basetype_UnsignedInteger32;

                    }

                    leaf Response {

                        type base:Basetype_UnsignedInteger32;

                    }

                    leaf RespPass {

                        type base:Basetype_UnsignedInteger32;

                    }

                    leaf RespFail {

                        type base:Basetype_UnsignedInteger32;

                    }

                    leaf RespGetData {

                        type base:Basetype_UnsignedInteger32;

                    }

                    leaf RespGetUser {

                        type base:Basetype_UnsignedInteger32;

                    }

                    leaf RespGetPass {

                        type base:Basetype_UnsignedInteger32;

                    }

                    leaf RespRestart {

                        type base:Basetype_UnsignedInteger32;

                    }

                    leaf RespErr {

                        type base:Basetype_UnsignedInteger32;

                    }

                    leaf RespFollow {

                        type base:Basetype_UnsignedInteger32;

                    }

                    leaf RespMalformed {

                        type base:Basetype_UnsignedInteger32;

                    }

                    leaf RespUnknownType {

                        type base:Basetype_UnsignedInteger32;

                    }

                    leaf RespDropped {

                        type base:Basetype_UnsignedInteger32;

                    }

                }

            }

            container AuthorServers {

                list AuthorServer {

                    key "VRF IpType Host Port";

                    leaf VRF {

                        type union {

                            type base:Basetype_EmptyString;

                            type base:Basetype_String {

                                length "1..31";

                            }

                        }

                    }

                    leaf IpType {

                        type enumeration {

                            enum 0;

                            enum 1;

                            enum 2;

                        }

                    }

                    leaf Host {

                        type base:Basetype_IpAddress;

                    }

                    leaf Port {

                        type base:Basetype_UnsignedInteger32 {

                            range "1..65535";

                        }

                    }

                    leaf LastRoundTripTime {

                        type base:Basetype_UnsignedInteger32;

                    }

                    leaf PendingRequest {

                        type base:Basetype_UnsignedInteger32;

                    }

                    leaf Timeout {

                        type base:Basetype_UnsignedInteger32;

                    }

                    leaf Request {

                        type base:Basetype_UnsignedInteger32;

                    }

                    leaf Response {

                        type base:Basetype_UnsignedInteger32;

                    }

                    leaf RespPassAdd {

                        type base:Basetype_UnsignedInteger32;

                    }

                    leaf RespPassRepl {

                        type base:Basetype_UnsignedInteger32;

                    }

                    leaf RespFail {

                        type base:Basetype_UnsignedInteger32;

                    }

                    leaf RespErr {

                        type base:Basetype_UnsignedInteger32;

                    }

                    leaf RespFollow {

                        type base:Basetype_UnsignedInteger32;

                    }

                    leaf RespMalformed {

                        type base:Basetype_UnsignedInteger32;

                    }

                    leaf RespUnknownType {

                        type base:Basetype_UnsignedInteger32;

                    }

                    leaf RespDropped {

                        type base:Basetype_UnsignedInteger32;

                    }

                }

            }

            container AcctServers {

                list AcctServer {

                    key "VRF IpType Host Port";

                    leaf VRF {

                        type union {

                            type base:Basetype_EmptyString;

                            type base:Basetype_String {

                                length "1..31";

                            }

                        }

                    }

                    leaf IpType {

                        type enumeration {

                            enum 0;

                            enum 1;

                            enum 2;

                        }

                    }

                    leaf Host {

                        type base:Basetype_IpAddress;

                    }

                    leaf Port {

                        type base:Basetype_UnsignedInteger32 {

                            range "1..65535";

                        }

                    }

                    leaf LastRoundTripTime {

                        type base:Basetype_UnsignedInteger32;

                    }

                    leaf PendingRequest {

                        type base:Basetype_UnsignedInteger32;

                    }

                    leaf Timeout {

                        type base:Basetype_UnsignedInteger32;

                    }

                    leaf Request {

                        type base:Basetype_UnsignedInteger32;

                    }

                    leaf ReqStart {

                        type base:Basetype_UnsignedInteger32;

                    }

                    leaf ReqStop {

                        type base:Basetype_UnsignedInteger32;

                    }

                    leaf ReqUpdate {

                        type base:Basetype_UnsignedInteger32;

                    }

                    leaf ReqStartAndUpdate {

                        type base:Basetype_UnsignedInteger32;

                    }

                    leaf ReqMore {

                        type base:Basetype_UnsignedInteger32;

                    }

                    leaf Response {

                        type base:Basetype_UnsignedInteger32;

                    }

                    leaf RespSuccess {

                        type base:Basetype_UnsignedInteger32;

                    }

                    leaf RespErr {

                        type base:Basetype_UnsignedInteger32;

                    }

                    leaf RespFollow {

                        type base:Basetype_UnsignedInteger32;

                    }

                    leaf RespMalformed {

                        type base:Basetype_UnsignedInteger32;

                    }

                    leaf RespUnknownType {

                        type base:Basetype_UnsignedInteger32;

                    }

                    leaf RespDropped {

                        type base:Basetype_UnsignedInteger32;

                    }

                }

            }

        }

        container GlobalNasIps {

            list GlobalNasIp {

                key "VRF IpType";

                leaf VRF {

                    type union {

                        type base:Basetype_EmptyString;

                        type base:Basetype_String {

                            length "1..31";

                        }

                    }

                }

                leaf IpType {

                    type base:Basetype_UnsignedInteger32 {

                        range "0..1";

                    }

                }

                leaf IpAddress {

                    type base:Basetype_IpAddress;

                }

            }

        }

        container Schemes {

            list Scheme {

                key "SchemeName";

                leaf SchemeName {

                    type base:Basetype_String {

                        length "1..32";

                    }

                }

                leaf RealAcctInterval {

                    type base:Basetype_UnsignedInteger32 {

                        range "0..60";

                    }

                }

                leaf TimeOut {

                    type base:Basetype_UnsignedInteger32 {

                        range "1..300";

                    }

                }

                leaf QuietTime {

                    type base:Basetype_UnsignedInteger32 {

                        range "1..255";

                    }

                }

                leaf UserNameFormat {

                    type base:Basetype_UnsignedInteger32 {

                        range "0..2";

                    }

                }

                leaf BytesUnit {

                    type base:Basetype_UnsignedInteger32 {

                        range "0..3";

                    }

                }

                leaf PacketsUint {

                    type base:Basetype_UnsignedInteger32 {

                        range "0..3";

                    }

                }

                leaf NasIpv4Address {

                    type base:Basetype_Ipv4Address;

                }

                leaf NasIpv6Address {

                    type base:Basetype_Ipv6Address;

                }

                leaf VRF {

                    type union {

                        type base:Basetype_EmptyString;

                        type base:Basetype_String {

                            length "1..31";

                        }

                    }

                }

            }

        }

        container AuthServers {

            list AuthServer {

                key "SchemeName Priority VRF IpType Host Port";

                leaf SchemeName {

                    type base:Basetype_String {

                        length "1..32";

                    }

                }

                leaf Priority {

                    type base:Basetype_UnsignedInteger32 {

                        range "0..1";

                    }

                }

                leaf VRF {

                    type union {

                        type base:Basetype_EmptyString;

                        type base:Basetype_String {

                            length "1..31";

                        }

                    }

                }

                leaf IpType {

                    type base:Basetype_UnsignedInteger32 {

                        range "0..2";

                    }

                }

                leaf Host {

                    type base:Basetype_OctectString;

                }

                leaf Port {

                    type union {

                        type base:Basetype_EmptyString;

                        type base:Basetype_UnsignedInteger32 {

                            range "1..65535";

                        }

                    }

                }

                leaf SingleConn {

                    type base:Basetype_Boolean;

                }

                leaf State {

                    type base:Basetype_UnsignedInteger32 {

                        range "0..1";

                    }

                }

            }

        }

        container AuthorServers {

            list AuthorServer {

                key "SchemeName Priority VRF IpType Host Port";

                leaf SchemeName {

                    type base:Basetype_String {

                        length "1..32";

                    }

                }

                leaf Priority {

                    type base:Basetype_UnsignedInteger32 {

                        range "0..1";

                    }

                }

                leaf VRF {

                    type union {

                        type base:Basetype_EmptyString;

                        type base:Basetype_String {

                            length "1..31";

                        }

                    }

                }

                leaf IpType {

                    type base:Basetype_UnsignedInteger32 {

                        range "0..2";

                    }

                }

                leaf Host {

                    type base:Basetype_OctectString;

                }

                leaf Port {

                    type union {

                        type base:Basetype_EmptyString;

                        type base:Basetype_UnsignedInteger32 {

                            range "1..65535";

                        }

                    }

                }

                leaf SingleConn {

                    type base:Basetype_Boolean;

                }

                leaf State {

                    type base:Basetype_UnsignedInteger32 {

                        range "0..1";

                    }

                }

            }

        }

        container AcctServers {

            list AcctServer {

                key "SchemeName Priority VRF IpType Host Port";

                leaf SchemeName {

                    type base:Basetype_String {

                        length "1..32";

                    }

                }

                leaf Priority {

                    type base:Basetype_UnsignedInteger32 {

                        range "0..1";

                    }

                }

                leaf VRF {

                    type union {

                        type base:Basetype_EmptyString;

                        type base:Basetype_String {

                            length "1..31";

                        }

                    }

                }

                leaf IpType {

                    type base:Basetype_UnsignedInteger32 {

                        range "0..2";

                    }

                }

                leaf Host {

                    type base:Basetype_OctectString;

                }

                leaf Port {

                    type union {

                        type base:Basetype_EmptyString;

                        type base:Basetype_UnsignedInteger32 {

                            range "1..65535";

                        }

                    }

                }

                leaf SingleConn {

                    type base:Basetype_Boolean;

                }

                leaf State {

                    type base:Basetype_UnsignedInteger32 {

                        range "0..1";

                    }

                }

            }

        }

        container PasswordLimit {

            leaf MinLen {

                type base:Basetype_UnsignedInteger32;

            }

            leaf MaxLen {

                type base:Basetype_UnsignedInteger32;

            }

            leaf MinTypeNum {

                type base:Basetype_UnsignedInteger32;

            }

        }

    }

}
