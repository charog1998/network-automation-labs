module H3C-mgroup-data {

    namespace "http://www.h3c.com/netconf/data:1.0";

    prefix "mgroup-data";

    import comware-basetype {

         prefix "base";

    }

    import comware-extension {

         prefix "ext";

    }

    organization "NEW H3C Technologies Co., Ltd.";

    contact "Website: http://www.h3c.com";

    description "The module entities for mgroup data.";

    revision 2019-12-20 {

        description "Initial revision.";

    }

    container MGROUP {

        config false;

        container Groups {

            description "Port priority table

                This table supports creating rows.";

            list Group {

                description "Row name";

                key "ID";

                leaf ID {

                    type base:Basetype_UnsignedInteger32 {

                        range "1..256";

                    }

                    description "Interface Index";

                }

                leaf Type {

                    type enumeration {

                        enum 1;

                        enum 2;

                        enum 3;

                    }

                    description "DSCP";

                }

                leaf Sampler {

                    type base:Basetype_String {

                        length "1..31";

                    }

                    description "DSCP";

                }

                leaf Status {

                    type enumeration {

                        enum 1;

                        enum 2;

                    }

                    description "Status";

                }

            }

        }

        container MonitorPort {

            description "Port priority trust mode table";

            list Group {

                description "Row name";

                key "ID";

                leaf ID {

                    type base:Basetype_UnsignedInteger32 {

                        range "1..256";

                    }

                    description "Interface Index";

                }

                leaf Port {

                    type base:Basetype_NameAndIndexUnion;

                    description "Interface Index";

                }

            }

        }

        container ReflectorPort {

            description "Port priority trust mode table";

            list Group {

                description "Row name";

                key "ID";

                leaf ID {

                    type base:Basetype_UnsignedInteger32 {

                        range "1..256";

                    }

                    description "Interface Index";

                }

                leaf Port {

                    type base:Basetype_NameAndIndexUnion;

                    description "Port priority trust mode";

                }

            }

        }

        container EgressPort {

            description "Port priority trust mode table";

            list Group {

                description "Row name";

                key "ID";

                leaf ID {

                    type base:Basetype_UnsignedInteger32 {

                        range "1..256";

                    }

                    description "Interface Index";

                }

                leaf Port {

                    type base:Basetype_NameAndIndexUnion;

                    description "Port priority trust mode";

                }

            }

        }

        container ProbeVlan {

            description "Port priority trust mode table";

            list Group {

                description "Row name";

                key "ID";

                leaf ID {

                    type base:Basetype_UnsignedInteger32 {

                        range "1..256";

                    }

                    description "Interface Index";

                }

                leaf VlanID {

                    type base:Basetype_UnsignedInteger32 {

                        range "1..4094";

                    }

                    description "Port priority trust mode";

                }

            }

        }

        container SourcePorts {

            description "Priority mapping table

                This table supports creating rows.";

            list SourcePort {

                description "Row name";

                key "ID IfIndex";

                leaf ID {

                    type base:Basetype_UnsignedInteger32 {

                        range "1..256";

                    }

                    description "Interface Index";

                }

                leaf IfIndex {

                    type base:Basetype_NameAndIndexUnion;

                    description "Interface Index";

                }

                leaf Direction {

                    type enumeration {

                        enum 1;

                        enum 2;

                        enum 3;

                    }

                    description "Port priority trust mode";

                }

            }

        }

    }

}
