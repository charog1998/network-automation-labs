module H3C-passwordcontrol-data {

    namespace "http://www.h3c.com/netconf/data:1.0";

    prefix "passwordcontrol-data";

    import comware-basetype {

         prefix "base";

    }

    import comware-extension {

         prefix "ext";

    }

    organization "NEW H3C Technologies Co., Ltd.";

    contact "Website: http://www.h3c.com";

    description "The module entities for passwordcontrol data.";

    revision 2019-12-20 {

        description "Initial revision.";

    }

    container PasswordControl {

        config false;

        container BlackLists {

            list BlackList {

                key "UserName IpType IpAddress";

                leaf UserName {

                    type base:Basetype_String {

                        length "1..55";

                    }

                }

                leaf IpType {

                    type base:Basetype_UnsignedInteger32 {

                        range "0..1";

                    }

                }

                leaf IpAddress {

                    type base:Basetype_IpAddress;

                }

                leaf LoginFailures {

                    type base:Basetype_UnsignedInteger32;

                }

                leaf LockState {

                    type base:Basetype_UnsignedInteger32 {

                        range "0..1";

                    }

                }

            }

        }

        container GlobalConfig {

            leaf GlobalEnableState {

                type base:Basetype_Boolean;

            }

            leaf GlobalNetworkEnableState {

                type base:Basetype_Boolean;

            }

            container Length {

                leaf State {

                    type base:Basetype_Boolean;

                }

                leaf MinLength {

                    type base:Basetype_UnsignedInteger32 {

                        range "4..32";

                    }

                }

            }

            container Composition {

                leaf State {

                    type base:Basetype_Boolean;

                }

                leaf TypeNumber {

                    type base:Basetype_UnsignedInteger32 {

                        range "1..4";

                    }

                }

                leaf PerTypeLen {

                    type base:Basetype_UnsignedInteger32 {

                        range "1..63";

                    }

                }

            }

            container Aging {

                leaf State {

                    type base:Basetype_Boolean;

                }

                leaf AgingTime {

                    type base:Basetype_UnsignedInteger32 {

                        range "1..365";

                    }

                }

            }

            container History {

                leaf State {

                    type base:Basetype_Boolean;

                }

                leaf MaxHistoryNumber {

                    type base:Basetype_UnsignedInteger32 {

                        range "2..15";

                    }

                }

            }

            leaf CheckSameChar {

                type base:Basetype_Boolean;

            }

            leaf CheckUserName {

                type base:Basetype_Boolean;

            }

            leaf AlertTime {

                type base:Basetype_UnsignedInteger32 {

                    range "1..30";

                }

            }

            leaf IdleTime {

                type base:Basetype_UnsignedInteger32 {

                    range "0..365";

                }

            }

            leaf UpdateInterval {

                type base:Basetype_UnsignedInteger32 {

                    range "0..168";

                }

            }

            container Expired {

                leaf DelayTime {

                    type base:Basetype_UnsignedInteger32 {

                        range "1..90";

                    }

                }

                leaf TryTimes {

                    type base:Basetype_UnsignedInteger32 {

                        range "0..10";

                    }

                }

            }

            container Attempt {

                leaf FailTimes {

                    type base:Basetype_UnsignedInteger32 {

                        range "2..10";

                    }

                }

                leaf Action {

                    type base:Basetype_UnsignedInteger32 {

                        range "0..2";

                    }

                }

                leaf LockTime {

                    type base:Basetype_UnsignedInteger32 {

                        range "1..360";

                    }

                }

            }

            leaf WeakPwdForceChange {

                type base:Basetype_Boolean;

            }

        }

        container Users {

            list User {

                key "UserName";

                leaf UserName {

                    type base:Basetype_String {

                        length "1..55";

                    }

                }

                leaf CheckSameChar {

                    type base:Basetype_Boolean;

                }

                leaf CheckUserName {

                    type base:Basetype_Boolean;

                }

                leaf MinLength {

                    type base:Basetype_UnsignedInteger32 {

                        range "4..32";

                    }

                }

                leaf AgingTime {

                    type base:Basetype_UnsignedInteger32 {

                        range "1..365";

                    }

                }

                container Composition {

                    leaf TypeNumber {

                        type base:Basetype_UnsignedInteger32 {

                            range "1..4";

                        }

                    }

                    leaf PerTypeLen {

                        type base:Basetype_UnsignedInteger32 {

                            range "1..63";

                        }

                    }

                }

                container Attempt {

                    leaf FailTimes {

                        type base:Basetype_UnsignedInteger32 {

                            range "2..10";

                        }

                    }

                    leaf Action {

                        type base:Basetype_UnsignedInteger32 {

                            range "0..2";

                        }

                    }

                    leaf LockTime {

                        type base:Basetype_UnsignedInteger32 {

                            range "1..360";

                        }

                    }

                }

            }

        }

        container NetworkUsers {

            list NetworkUser {

                key "UserName";

                leaf UserName {

                    type base:Basetype_String {

                        length "1..55";

                    }

                }

                leaf CheckSameChar {

                    type base:Basetype_Boolean;

                }

                leaf CheckUserName {

                    type base:Basetype_Boolean;

                }

                leaf MinLength {

                    type base:Basetype_UnsignedInteger32 {

                        range "4..32";

                    }

                }

                container Composition {

                    leaf TypeNumber {

                        type base:Basetype_UnsignedInteger32 {

                            range "1..4";

                        }

                    }

                    leaf PerTypeLen {

                        type base:Basetype_UnsignedInteger32 {

                            range "1..63";

                        }

                    }

                }

            }

        }

        container Super {

            leaf MinLength {

                type base:Basetype_UnsignedInteger32 {

                    range "4..63";

                }

            }

            leaf AgingTime {

                type base:Basetype_UnsignedInteger32 {

                    range "1..365";

                }

            }

            container Composition {

                leaf TypeNumber {

                    type base:Basetype_UnsignedInteger32 {

                        range "1..4";

                    }

                }

                leaf PerTypeLen {

                    type base:Basetype_UnsignedInteger32 {

                        range "1..63";

                    }

                }

            }

        }

        container UserGroups {

            list UserGroup {

                key "UserGroupName";

                leaf UserGroupName {

                    type base:Basetype_String {

                        length "1..32";

                    }

                }

                leaf CheckSameChar {

                    type base:Basetype_Boolean;

                }

                leaf CheckUserName {

                    type base:Basetype_Boolean;

                }

                leaf MinLength {

                    type base:Basetype_UnsignedInteger32 {

                        range "4..32";

                    }

                }

                leaf AgingTime {

                    type base:Basetype_UnsignedInteger32 {

                        range "1..365";

                    }

                }

                container Composition {

                    leaf TypeNumber {

                        type base:Basetype_UnsignedInteger32 {

                            range "1..4";

                        }

                    }

                    leaf PerTypeLen {

                        type base:Basetype_UnsignedInteger32 {

                            range "1..63";

                        }

                    }

                }

                container Attempt {

                    leaf FailTimes {

                        type base:Basetype_UnsignedInteger32 {

                            range "2..10";

                        }

                    }

                    leaf Action {

                        type base:Basetype_UnsignedInteger32 {

                            range "0..2";

                        }

                    }

                    leaf LockTime {

                        type base:Basetype_UnsignedInteger32 {

                            range "1..360";

                        }

                    }

                }

            }

        }

        container Specification {

            leaf MinLength {

                type base:Basetype_UnsignedInteger32;

            }

            leaf MinTypeNumber {

                type base:Basetype_UnsignedInteger32;

            }

            leaf MaxPerTypeLen {

                type base:Basetype_UnsignedInteger32;

            }

        }

    }

}
