module H3C-identity-data {

    namespace "http://www.h3c.com/netconf/data:1.0";

    prefix "identity-data";

    import comware-basetype {

         prefix "base";

    }

    import comware-extension {

         prefix "ext";

    }

    organization "NEW H3C Technologies Co., Ltd.";

    contact "Website: http://www.h3c.com";

    description "The module entities for identity data.";

    revision 2019-12-20 {

        description "Initial revision.";

    }

    container Identity {

        config false;

        container Policies {

            config false;

            container RestfulPolicies {

                list RestfulPolicy {

                    key "PolicyName RestfulServerName";

                    leaf PolicyName {

                        type base:Basetype_String {

                            length "1..31";

                        }

                    }

                    leaf RestfulServerName {

                        type base:Basetype_String {

                            length "1..31";

                        }

                    }

                }

            }

            container LDAPPolicies {

                list LDAPPolicy {

                    key "PolicyName LDAPSchemeName";

                    leaf PolicyName {

                        type base:Basetype_String {

                            length "1..31";

                        }

                    }

                    leaf LDAPSchemeName {

                        type base:Basetype_String {

                            length "1..32";

                        }

                    }

                }

            }

        }

        container IdentityEnable {

            leaf Enable {

                type base:Basetype_Boolean;

            }

        }

        container StaticUsers {

            list StaticUser {

                key "DomainName Name IpType IpAddress MacAddress";

                leaf DomainName {

                    type union {

                        type base:Basetype_EmptyString;

                        type base:Basetype_String {

                            length "1..255";

                        }

                    }

                }

                leaf Name {

                    type base:Basetype_String {

                        length "1..55";

                    }

                }

                leaf IpType {

                    type base:Basetype_UnsignedInteger32 {

                        range "0..1";

                    }

                }

                leaf IpAddress {

                    type base:Basetype_IpAddress;

                }

                leaf MacAddress {

                    type union {

                        type base:Basetype_EmptyString;

                        type base:Basetype_MacAddress;

                    }

                }

            }

        }

        container OnlineUsers {

            list OnlineUser {

                key "DomainName UserName IpAddress MacAddress Position";

                leaf DomainName {

                    type union {

                        type base:Basetype_EmptyString;

                        type base:Basetype_String {

                            length "1..255";

                        }

                    }

                }

                leaf UserName {

                    type base:Basetype_String {

                        length "1..55";

                    }

                }

                leaf IpAddress {

                    type base:Basetype_IpAddress;

                }

                leaf MacAddress {

                    type base:Basetype_MacAddress;

                }

                leaf Position {

                    type base:Basetype_UnsignedInteger32 {

                        range "0..4294967295";

                    }

                }

                leaf Type {

                    type base:Basetype_UnsignedInteger32 {

                        range "1..3";

                    }

                }

            }

        }

        container AccountUsers {

            list AccountUser {

                key "DomainName UserName";

                leaf DomainName {

                    type union {

                        type base:Basetype_EmptyString;

                        type base:Basetype_String {

                            length "1..255";

                        }

                    }

                }

                leaf UserName {

                    type base:Basetype_String {

                        length "1..55";

                    }

                }

            }

        }

        container AccountGroups {

            list AccountGroup {

                key "DomainName GroupName";

                leaf DomainName {

                    type union {

                        type base:Basetype_EmptyString;

                        type base:Basetype_String {

                            length "1..255";

                        }

                    }

                }

                leaf GroupName {

                    type base:Basetype_String {

                        length "1..200";

                    }

                }

                leaf PureGroupName {

                    type base:Basetype_String {

                        length "1..200";

                    }

                }

            }

        }

        container DownloadOnlineUser {

            list OnlineUser {

                key "domain userName vpnName userIp macAddr Position";

                leaf domain {

                    type union {

                        type base:Basetype_EmptyString;

                        type base:Basetype_String {

                            length "1..255";

                        }

                    }

                }

                leaf userName {

                    type base:Basetype_String {

                        length "1..55";

                    }

                }

                leaf vpnName {

                    type union {

                        type base:Basetype_EmptyString;

                        type base:Basetype_String {

                            length "1..31";

                        }

                    }

                }

                leaf userIp {

                    type base:Basetype_IpAddress;

                }

                leaf macAddr {

                    type union {

                        type base:Basetype_EmptyString;

                        type base:Basetype_MacAddress;

                    }

                }

                leaf Position {

                    type base:Basetype_UnsignedInteger32 {

                        range "0..4294967295";

                    }

                }

            }

        }

        container DownloadOfflineUser {

            list OfflineUser {

                key "domain userName vpnName userIp macAddr";

                leaf domain {

                    type union {

                        type base:Basetype_EmptyString;

                        type base:Basetype_String {

                            length "1..255";

                        }

                    }

                }

                leaf userName {

                    type base:Basetype_String {

                        length "1..55";

                    }

                }

                leaf vpnName {

                    type union {

                        type base:Basetype_EmptyString;

                        type base:Basetype_String {

                            length "1..31";

                        }

                    }

                }

                leaf userIp {

                    type base:Basetype_IpAddress;

                }

                leaf macAddr {

                    type union {

                        type base:Basetype_EmptyString;

                        type base:Basetype_MacAddress;

                    }

                }

            }

        }

        container RestfulServers {

            list RestfulServer {

                key "ServerName";

                leaf ServerName {

                    type base:Basetype_String {

                        length "1..31";

                    }

                }

                leaf LoginName {

                    type union {

                        type base:Basetype_EmptyString;

                        type base:Basetype_String {

                            length "1..55";

                        }

                    }

                }

                leaf VpnName {

                    type union {

                        type base:Basetype_EmptyString;

                        type base:Basetype_String {

                            length "1..31";

                        }

                    }

                }

                leaf GetUserDatabase {

                    type union {

                        type base:Basetype_EmptyString;

                        type base:Basetype_OctectString {

                            length "1..255";

                        }

                    }

                }

                leaf GetUserGroupDatabase {

                    type union {

                        type base:Basetype_EmptyString;

                        type base:Basetype_OctectString {

                            length "1..255";

                        }

                    }

                }

                leaf GetOnlineUser {

                    type union {

                        type base:Basetype_EmptyString;

                        type base:Basetype_OctectString {

                            length "1..255";

                        }

                    }

                }

                leaf PutOnlineUser {

                    type union {

                        type base:Basetype_EmptyString;

                        type base:Basetype_OctectString {

                            length "1..255";

                        }

                    }

                }

                leaf PutOfflineUser {

                    type union {

                        type base:Basetype_EmptyString;

                        type base:Basetype_OctectString {

                            length "1..255";

                        }

                    }

                }

                leaf DetectEnable {

                    type base:Basetype_Boolean;

                }

                leaf DetectInterval {

                    type base:Basetype_UnsignedInteger32 {

                        range "1..10";

                    }

                }

                leaf DetectMaxCount {

                    type base:Basetype_UnsignedInteger32 {

                        range "1..5";

                    }

                }

                leaf ConnectState {

                    type base:Basetype_Boolean;

                }

            }

        }

        container UserImportPolicies {

            list UserImportPolicy {

                key "PolicyName";

                leaf PolicyName {

                    type base:Basetype_String {

                        length "1..31";

                    }

                }

                leaf UpdateInterval {

                    type base:Basetype_UnsignedInteger32 {

                        range "1..65536";

                    }

                }

                leaf ImportType {

                    type base:Basetype_UnsignedInteger32 {

                        range "1..3";

                    }

                }

            }

        }

        container UserAccountsAutoImport {

            list UserAccountAutoImport {

                key "PolicyName";

                leaf PolicyName {

                    type base:Basetype_String {

                        length "1..31";

                    }

                }

                leaf Auto {

                    type base:Basetype_Boolean;

                }

            }

        }

        container OnlineUserDomFormat {

            leaf DomainFormat {

                type base:Basetype_UnsignedInteger32 {

                    range "1..3";

                }

            }

        }

        container TopUsers {

            list TopUser {

                key "DomainName UserName";

                leaf DomainName {

                    type union {

                        type base:Basetype_EmptyString;

                        type base:Basetype_String {

                            length "1..255";

                        }

                    }

                }

                leaf UserName {

                    type base:Basetype_String {

                        length "1..55";

                    }

                }

            }

        }

        container TopGroups {

            list TopGroup {

                key "DomainName GroupName";

                leaf DomainName {

                    type union {

                        type base:Basetype_EmptyString;

                        type base:Basetype_String {

                            length "1..255";

                        }

                    }

                }

                leaf GroupName {

                    type base:Basetype_String {

                        length "1..200";

                    }

                }

                leaf PureGroupName {

                    type base:Basetype_String {

                        length "1..200";

                    }

                }

            }

        }

        container ParentGroups {

            list ParentGroup {

                key "DomainName UserName GroupName";

                leaf DomainName {

                    type union {

                        type base:Basetype_EmptyString;

                        type base:Basetype_String {

                            length "1..255";

                        }

                    }

                }

                leaf UserName {

                    type base:Basetype_String {

                        length "1..55";

                    }

                }

                leaf GroupName {

                    type base:Basetype_String {

                        length "1..200";

                    }

                }

                leaf PureGroupName {

                    type base:Basetype_String {

                        length "1..200";

                    }

                }

            }

        }

        container MemberUsers {

            list MemberUser {

                key "DomainName GroupName UserName";

                leaf DomainName {

                    type union {

                        type base:Basetype_EmptyString;

                        type base:Basetype_String {

                            length "1..255";

                        }

                    }

                }

                leaf GroupName {

                    type base:Basetype_String {

                        length "1..200";

                    }

                }

                leaf UserName {

                    type base:Basetype_String {

                        length "1..255";

                    }

                }

            }

        }

        container MemberGroups {

            list MemberGroup {

                key "DomainName GroupName MemberGroup";

                leaf DomainName {

                    type union {

                        type base:Basetype_EmptyString;

                        type base:Basetype_String {

                            length "1..255";

                        }

                    }

                }

                leaf GroupName {

                    type base:Basetype_String {

                        length "1..200";

                    }

                }

                leaf MemberGroup {

                    type base:Basetype_String {

                        length "1..200";

                    }

                }

                leaf PureMemGroupName {

                    type base:Basetype_String {

                        length "1..200";

                    }

                }

            }

        }

        container SecManageServers {

            list SecManageServer {

                key "ServerName";

                leaf ServerName {

                    type base:Basetype_String {

                        length "1..31";

                    }

                }

                leaf ListenPort {

                    type union {

                        type base:Basetype_EmptyString;

                        type base:Basetype_UnsignedInteger32 {

                            range "1..65535";

                        }

                    }

                }

                leaf EncrypAlgorithm {

                    type union {

                        type base:Basetype_EmptyString;

                        type base:Basetype_UnsignedInteger32 {

                            range "0..1";

                        }

                    }

                }

            }

        }

        container SecManageIPs {

            list SecManageIP {

                key "ServerName Ipv4Address";

                leaf ServerName {

                    type base:Basetype_String {

                        length "1..31";

                    }

                }

                leaf Ipv4Address {

                    type base:Basetype_Ipv4Address;

                }

            }

        }

        container Domains {

            list Domain {

                key "DomainName";

                leaf DomainName {

                    type base:Basetype_String {

                        length "1..255";

                    }

                }

            }

        }

        container ImportAccountProgress {

            leaf UsersCount {

                type base:Basetype_UnsignedInteger32;

            }

            leaf GroupsCount {

                type base:Basetype_UnsignedInteger32;

            }

            leaf ImportState {

                type base:Basetype_UnsignedInteger32 {

                    range "0..2";

                }

            }

        }

        container ImportOnlineUserProgress {

            leaf UsersCount {

                type base:Basetype_UnsignedInteger32;

            }

            leaf ImportState {

                type base:Basetype_UnsignedInteger32 {

                    range "0..2";

                }

            }

        }

    }

}
