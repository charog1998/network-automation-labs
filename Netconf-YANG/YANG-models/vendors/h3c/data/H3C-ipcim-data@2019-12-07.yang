module H3C-ipcim-data {

    namespace "http://www.h3c.com/netconf/data:1.0";

    prefix "ipcim-data";

    import comware-basetype {

         prefix "base";

    }

    import comware-extension {

         prefix "ext";

    }

    organization "NEW H3C Technologies Co., Ltd.";

    contact "Website: http://www.h3c.com";

    description "The module entities for ipcim data.";

    revision 2019-12-07 {

        description "Initial revision.";

    }

    container IPCIM {

        config false;

        container IpSourceBindingInterface {

            list SourceBinding {

                key "IfIndex Ipv4Address MacAddress VLANID";

                leaf IfIndex {

                    type base:Basetype_NameAndIndexUnion;

                }

                leaf Ipv4Address {

                    type base:Basetype_Ipv4Address;

                }

                leaf MacAddress {

                    type base:Basetype_MacAddress;

                }

                leaf VLANID {

                    type base:Basetype_UnsignedInteger32 {

                        range "0..4094";

                    }

                }

            }

        }

        container IpVerifySource {

            list VerifySource {

                key "IfIndex";

                leaf IfIndex {

                    type base:Basetype_NameAndIndexUnion;

                }

                leaf VerifyIpAddress {

                    type base:Basetype_Boolean;

                }

                leaf VerifyMacAddress {

                    type base:Basetype_Boolean;

                }

            }

        }

    }

}
