module H3C-ping-event {

    namespace "http://www.h3c.com/netconf/event:1.0/ping:1.0";

    prefix "ping-event";

    import comware-basetype {

         prefix "base";

    }

    import comware-extension {

         prefix "ext";

    }

    organization "NEW H3C Technologies Co., Ltd.";

    contact "Website: http://www.h3c.com";

    description "The module entities for ping event.";

    revision 2019-12-17 {

        description "Initial revision.";

    }

}
