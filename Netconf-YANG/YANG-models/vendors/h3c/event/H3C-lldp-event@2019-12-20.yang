module H3C-lldp-event {

    namespace "http://www.h3c.com/netconf/event:1.0/lldp:1.0";

    prefix "lldp-event";

    import comware-basetype {

         prefix "base";

    }

    import comware-extension {

         prefix "ext";

    }

    organization "NEW H3C Technologies Co., Ltd.";

    contact "Website: http://www.h3c.com";

    description "The module entities for lldp event.";

    revision 2019-12-20 {

        description "Initial revision.";

    }

    notification NeighborEvent {

        container Neighbor {

            leaf IfName {

                type base:Basetype_OctectString255;

                description "interface name";

            }

            leaf AgentID {

                type enumeration {

                    enum 1;

                    enum 2;

                    enum 3;

                }

                description "LLDP agent ID";

            }

            leaf NeighborChassisId {

                type base:Basetype_OctectString255;

                description "chassis identifier, a string of 0 to 255 characters";

            }

            leaf NeighborPortId {

                type base:Basetype_OctectString255;

                description "port identifier, a string of 0 to 255 characters";

            }

            leaf Neighborevent {

                type enumeration {

                    enum 1;

                    enum 2;

                    enum 3;

                }

                description "neighbor event type";

            }

            leaf SystemName {

                type base:Basetype_OctectString255;

                description "system name, a string of 0 to 255 characters";

            }

            leaf SystemCapability {

                type base:Basetype_UnsignedInteger32 {

                    range "0..65535";

                }

                description "Protocol system capability";

            }

            leaf SystemEnableCapability {

                type base:Basetype_UnsignedInteger32 {

                    range "0..65535";

                }

                description "Protocol system System Enable Capability";

            }

            leaf SystemDescription {

                type base:Basetype_OctectString255;

                description "system description, a string of 0 to 255 characters";

            }

        }

    }

}
