module H3C-poe-event {

    namespace "http://www.h3c.com/netconf/event:1.0/poe:1.0";

    prefix "poe-event";

    import comware-basetype {

         prefix "base";

    }

    import comware-extension {

         prefix "ext";

    }

    organization "NEW H3C Technologies Co., Ltd.";

    contact "Website: http://www.h3c.com";

    description "The module entities for poe event.";

    revision 2019-12-09 {

        description "Initial revision.";

    }

    notification PoEPortEvent {

        container PoEPort {

            leaf PSEID {

                type base:Basetype_UnsignedInteger32;

                description "PSE index.";

            }

            leaf InterfaceName {

                type base:Basetype_InterfaceName;

                description "Interface name.";

            }

        }

    }

}
