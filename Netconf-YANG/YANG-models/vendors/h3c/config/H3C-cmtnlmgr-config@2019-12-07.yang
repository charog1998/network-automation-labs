module H3C-cmtnlmgr-config {

    namespace "http://www.h3c.com/netconf/config:1.0";

    prefix "cmtnlmgr-config";

    import comware-basetype {

         prefix "base";

    }

    import comware-extension {

         prefix "ext";

    }

    organization "NEW H3C Technologies Co., Ltd.";

    contact "Website: http://www.h3c.com";

    description "The module entities for cmtnlmgr config.";

    revision 2019-12-07 {

        description "Initial revision.";

    }

    container Cmtnlmgr {

        container CloudDomainName {

            leaf DomainName {

                type base:Basetype_String {

                    length "1..253";

                }

            }

        }

        container CloudBackupDomain {

            list Domain {

                key "DomainName";

                leaf DomainName {

                    type base:Basetype_String {

                        length "1..253";

                    }

                }

            }

        }

        container CloudPort {

            leaf Port {

                type base:Basetype_UnsignedInteger32 {

                    range "1..65535";

                }

            }

        }

    }

}
