module H3C-ddns-config {

    namespace "http://www.h3c.com/netconf/config:1.0";

    prefix "ddns-config";

    import comware-basetype {

         prefix "base";

    }

    import comware-extension {

         prefix "ext";

    }

    organization "NEW H3C Technologies Co., Ltd.";

    contact "Website: http://www.h3c.com";

    description "The module entities for ddns config.";

    revision 2019-12-07 {

        description "Initial revision.";

    }

    container DDNS {

        container DDNSPolicy {

            list Policy {

                key "PolicyName";

                leaf PolicyName {

                    type base:Basetype_String {

                        length "1..32";

                    }

                }

                leaf URL {

                    type base:Basetype_URLString {

                        length "1..240";

                    }

                }

                leaf IntervalDay {

                    type base:Basetype_UnsignedInteger32 {

                        range "0..365";

                    }

                }

                leaf IntervalHour {

                    type base:Basetype_UnsignedInteger32 {

                        range "0..23";

                    }

                }

                leaf IntervalMinute {

                    type base:Basetype_UnsignedInteger32 {

                        range "0..59";

                    }

                }

                leaf Username {

                    type base:Basetype_String {

                        length "1..32";

                    }

                }

                leaf Password {

                    type base:Basetype_String {

                        length "1..32";

                    }

                }

                leaf Method {

                    type enumeration {

                        enum 0;

                        enum 1;

                    }

                }

                leaf SSLClientPolicy {

                    type base:Basetype_String {

                        length "1..31";

                    }

                }

            }

        }

        container DDNSIfApply {

            list IfApply {

                key "IfIndex PolicyName";

                leaf IfIndex {

                    type base:Basetype_NameAndIndexUnion;

                }

                leaf PolicyName {

                    type base:Basetype_String {

                        length "1..32";

                    }

                }

                leaf FQDN {

                    type base:Basetype_String {

                        length "1..253";

                    }

                }

            }

        }

    }

}
