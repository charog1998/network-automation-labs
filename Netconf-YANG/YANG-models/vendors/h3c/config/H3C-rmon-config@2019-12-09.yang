module H3C-rmon-config {

    namespace "http://www.h3c.com/netconf/config:1.0";

    prefix "rmon-config";

    import comware-basetype {

         prefix "base";

    }

    import comware-extension {

         prefix "ext";

    }

    organization "NEW H3C Technologies Co., Ltd.";

    contact "Website: http://www.h3c.com";

    description "The module entities for rmon config.";

    revision 2019-12-09 {

        description "Initial revision.";

    }

    container RMON {

        container EtherStats {

            description "RMON EtherStats

                This table supports creating rows.";

            list Statistic {

                description "Rowname";

                key "Index";

                leaf Index {

                    type base:Basetype_UnsignedInteger32 {

                        range "1..65535";

                    }

                    description "Entry index";

                }

                leaf DataSource {

                    type base:Basetype_String;

                    description "The particular ethernet interface to be sampled.";

                }

                leaf Owner {

                    type base:Basetype_String {

                        length "1..127";

                    }

                    description "The entity that configured this entry.";

                }

                leaf TemporaryStatus {

                    type base:Basetype_Boolean;

                    description "The status of this entry.";

                }

            }

        }

        container EtherHistoryControls {

            description "rmon EtherHistoryControls infomations

                This table supports creating rows.";

            list Control {

                description "Rowname";

                key "Index";

                leaf Index {

                    type base:Basetype_UnsignedInteger32 {

                        range "1..65535";

                    }

                    description "EtherHistoryControls Index";

                }

                leaf DataSource {

                    type base:Basetype_String;

                    description "The source of the data for which

                          historical data was sampled.";

                }

                leaf BucketsRequested {

                    type base:Basetype_UnsignedInteger32 {

                        range "1..65535";

                    }

                    description "The requested number of records

                          to be saved for each interface.";

                }

                leaf Interval {

                    type base:Basetype_UnsignedInteger32 {

                        range "1..3600";

                    }

                    description "The sample interval. Unit: second.";

                }

                leaf Owner {

                    type base:Basetype_String {

                        length "1..127";

                    }

                    description "The entity that configured this entry.";

                }

                leaf TemporaryStatus {

                    type base:Basetype_Boolean;

                    description "The status of this entry.";

                }

            }

        }

        container Alarms {

            description "Rmon Alarms information

                This table supports creating rows.";

            list Alarm {

                description "Rowname";

                key "Index";

                leaf Index {

                    type base:Basetype_UnsignedInteger32 {

                        range "1..65535";

                    }

                    description "Entry index";

                }

                leaf Interval {

                    type base:Basetype_UnsignedInteger32 {

                        range "5..65535";

                    }

                    description "The interval over which the data is sampled and compared with the rising and falling thresholds.";

                }

                leaf Variable {

                    type base:Basetype_String;

                    description "A comment describing this event entry.";

                }

                leaf SampleType {

                    type enumeration {

                        enum 1;

                        enum 2;

                    }

                    description "Alarms SampleType";

                }

                leaf StartupAlarm {

                    type enumeration {

                        enum 1;

                        enum 2;

                        enum 3;

                    }

                    description "The alarm that may be sent when this entry is first set to valid.";

                }

                leaf RisingThreshold {

                    type base:Basetype_Integer32;

                    description "A threshold for the sampled statistic.";

                }

                leaf FallingThreshold {

                    type base:Basetype_Integer32;

                    description "A threshold for the sampled statistic.";

                }

                leaf RisingEventIndex {

                    type base:Basetype_UnsignedInteger32 {

                        range "0..65535";

                    }

                    description "The index in RMON/Events that is used when a rising threshold is crossed.";

                }

                leaf FallingEventIndex {

                    type base:Basetype_UnsignedInteger32 {

                        range "0..65535";

                    }

                    description "The index in RMON/Events that is used when a falling threshold is crossed.";

                }

                leaf Owner {

                    type base:Basetype_String {

                        length "1..127";

                    }

                    description "The entity that configured this entry.";

                }

                leaf TemporaryStatus {

                    type base:Basetype_Boolean;

                    description "Events TemporaryStatus.";

                }

            }

        }

        container Events {

            description "Rmon events information

                This table supports creating rows.";

            list Event {

                description "Rowname";

                key "Index";

                leaf Index {

                    type base:Basetype_UnsignedInteger32 {

                        range "1..65535";

                    }

                    description "Entry index";

                }

                leaf Description {

                    type base:Basetype_String {

                        length "1..127";

                    }

                    description "A comment describing this event entry.";

                }

                leaf Type {

                    type enumeration {

                        enum 1;

                        enum 2;

                        enum 3;

                        enum 4;

                    }

                    description "The type of notification that the probe will make about this event.

                          Enumeration.

                          1—None

                          2—Log

                          3—SnmpTrap

                          4—LogAndTrap";

                }

                leaf Community {

                    type base:Basetype_String {

                        length "1..127";

                    }

                    description "Rmon Community";

                }

                leaf Owner {

                    type base:Basetype_String {

                        length "1..127";

                    }

                    description "The entity that configured this entry.";

                }

                leaf TemporaryStatus {

                    type base:Basetype_Boolean;

                    description "Events TemporaryStatus.";

                }

            }

        }

        container UsrHistoryControls {

            description "UsrHistoryControls table

                This table supports creating rows.";

            list Control {

                description "rowname";

                key "Index";

                leaf Index {

                    type base:Basetype_UnsignedInteger32 {

                        range "1..65535";

                    }

                    description "index number";

                }

                leaf MaxObjects {

                    type base:Basetype_UnsignedInteger32 {

                        range "1..65535";

                    }

                    description "The max number of objects to be sampled.";

                }

                container Objects {

                    leaf Variable {

                        type base:Basetype_String;

                        description "The object identifier of the particular variable to be sampled";

                    }

                    leaf SampleType {

                        type enumeration {

                            enum 1;

                            enum 2;

                        }

                        description "The method of sampling the selected variables.

                                Enumeration.

                                1—AbsoluteValue

                                2—DeltaValue";

                    }

                }

                leaf BucketsRequested {

                    type base:Basetype_UnsignedInteger32 {

                        range "1..65535";

                    }

                    description "The requested number of records to be saved in UsrHistorySamples";

                }

                leaf Interval {

                    type base:Basetype_UnsignedInteger32 {

                        range "1..2147483647";

                    }

                    description "The sample interval";

                }

                leaf Owner {

                    type base:Basetype_String {

                        length "1..127";

                    }

                    description "The entity that configured this entry";

                }

                leaf TemporaryStatus {

                    type base:Basetype_Boolean;

                    description "The status of this entry";

                }

            }

        }

        container ExtAlarms {

            description "RMON ExtAlarms

                This table supports creating rows.";

            list Alarm {

                description "Rowname";

                key "Index";

                leaf Index {

                    type base:Basetype_UnsignedInteger32 {

                        range "1..65535";

                    }

                    description "Entry index";

                }

                leaf Interval {

                    type base:Basetype_UnsignedInteger32 {

                        range "10..65535";

                    }

                    description "The interval over which the data is sampled and compared with the rising and falling thresholds.

                          Unit: second.";

                }

                leaf Variable {

                    type base:Basetype_String;

                    description "The object identifier of the particular variable to be sampled.";

                }

                leaf Description {

                    type base:Basetype_String {

                        length "1..127";

                    }

                    description "A comment describing this alarm entry.";

                }

                leaf SampleType {

                    type enumeration {

                        enum 1;

                        enum 2;

                    }

                    description "The method of sampling the selected variable and calculating the value

                          to be compared against the thresholds.

                          1—AbsoluteValue

                          2—DeltaValue";

                }

                leaf StartupAlarm {

                    type enumeration {

                        enum 1;

                        enum 2;

                        enum 3;

                    }

                    description "The alarm that may be sent when this entry is first set to valid.

                          1—RisingAlarm

                          2—FallingAlarm

                          3—RisingOrFallingAlarm";

                }

                leaf RisingThreshold {

                    type base:Basetype_Integer32;

                    description "A rising threshold for the sampled statistic.";

                }

                leaf FallingThreshold {

                    type base:Basetype_Integer32;

                    description "A rising threshold for the sampled statistic.";

                }

                leaf RisingEvtIndex {

                    type base:Basetype_UnsignedShort;

                    description "The index in RMON/Events that is used when a rising threshold is crossed.";

                }

                leaf FallingEvtIndex {

                    type base:Basetype_UnsignedShort;

                    description "The index in RMON/Events that is used when a falling threshold is crossed.";

                }

                leaf StatCycle {

                    type base:Basetype_UnsignedInteger32 {

                        range "0..4294967";

                    }

                    description "The lifetime starts when an alarm entry is set in valid state.

                          Unit: second.";

                }

                leaf StatType {

                    type enumeration {

                        enum 1;

                        enum 2;

                    }

                    description "Type of statistic period.

                          1—Forever

                          2—During";

                }

                leaf Owner {

                    type base:Basetype_String {

                        length "1..127";

                    }

                    description "The entity that configured this entry.";

                }

                leaf TemporaryStatus {

                    type base:Basetype_Boolean;

                    description "The status of this entry.";

                }

            }

        }

    }

}
