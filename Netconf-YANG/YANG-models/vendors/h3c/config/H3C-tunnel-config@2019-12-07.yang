module H3C-tunnel-config {

    namespace "http://www.h3c.com/netconf/config:1.0";

    prefix "tunnel-config";

    import comware-basetype {

         prefix "base";

    }

    import comware-extension {

         prefix "ext";

    }

    organization "NEW H3C Technologies Co., Ltd.";

    contact "Website: http://www.h3c.com";

    description "The module entities for tunnel config.";

    revision 2019-12-07 {

        description "Initial revision.";

    }

    container TUNNEL {

        container Tunnels {

            list Tunnel {

                key "ID";

                leaf ID {

                    type base:Basetype_UnsignedInteger32;

                }

                leaf Mode {

                    type base:Basetype_UnsignedInteger32 {

                        range "1..64";

                    }

                }

                container IPv4Addr {

                    leaf SrcAddr {

                        type base:Basetype_Ipv4Address;

                    }

                    leaf SrcIfIndex {

                        type base:Basetype_NameAndIndexUnion;

                    }

                    leaf DstAddr {

                        type base:Basetype_Ipv4Address;

                    }

                }

                container IPv6Addr {

                    leaf SrcAddr {

                        type base:Basetype_Ipv6Address;

                    }

                    leaf SrcIfIndex {

                        type base:Basetype_NameAndIndexUnion;

                    }

                    leaf DstAddr {

                        type base:Basetype_Ipv6Address;

                    }

                }

                leaf Tos {

                    type base:Basetype_UnsignedInteger32 {

                        range "0..255";

                    }

                }

                leaf OutIfIndex {

                    type base:Basetype_NameAndIndexUnion;

                }

                leaf Dfbit {

                    type base:Basetype_Boolean;

                }

                leaf Ttl {

                    type base:Basetype_UnsignedInteger32 {

                        range "1..255";

                    }

                }

                container Keepalive {

                    leaf Interval {

                        type base:Basetype_UnsignedInteger32 {

                            range "1..32767";

                        }

                    }

                    leaf Times {

                        type base:Basetype_UnsignedInteger32 {

                            range "1..255";

                        }

                    }

                }

                leaf EncapLimit {

                    type base:Basetype_UnsignedInteger32 {

                        range "0..10";

                    }

                }

                leaf VRF {

                    type base:Basetype_String {

                        length "1..31";

                    }

                }

                container GRE {

                    leaf Key {

                        type base:Basetype_UnsignedInteger32 {

                            range "0..4294967295";

                        }

                    }

                    leaf Checksum {

                        type base:Basetype_Boolean;

                    }

                    leaf VpcEnable {

                        type base:Basetype_Boolean;

                    }

                    leaf P2MPTemplate {

                        type base:Basetype_String {

                            length "1..31";

                        }

                    }

                }

                leaf ServiceClass {

                    type base:Basetype_UnsignedInteger32 {

                        range "0..7";

                    }

                }

                container P2MP {

                    leaf AgingTime {

                        type base:Basetype_UnsignedInteger32 {

                            range "1..86400";

                        }

                    }

                    leaf BackupTunnel {

                        type base:Basetype_UnsignedInteger32;

                    }

                    leaf BranchIPv4NetMaskLength {

                        type base:Basetype_UnsignedInteger32 {

                            range "0..32";

                        }

                    }

                    leaf BranchIPv6NetMaskLength {

                        type base:Basetype_UnsignedInteger32 {

                            range "0..128";

                        }

                    }

                }

                container StaticRoute {

                    leaf Enable {

                        type base:Basetype_Boolean;

                    }

                    leaf Preference {

                        type base:Basetype_UnsignedInteger32 {

                            range "1..255";

                        }

                    }

                }

                leaf PathMtu {

                    type base:Basetype_Boolean;

                }

            }

        }

        container GlobalConfig {

            leaf VxlanUdpPort {

                type base:Basetype_UnsignedInteger32 {

                    range "1..65535";

                }

            }

            leaf DropInvalidChksumPkt {

                type base:Basetype_Boolean;

            }

            leaf VxlanIpForward {

                type base:Basetype_Boolean;

            }

            leaf FlowStatEnable {

                type base:Basetype_Boolean;

            }

            leaf FlowStatInterval {

                type base:Basetype_UnsignedInteger32 {

                    range "5..300";

                }

            }

        }

        container VXLANBFDs {

            list VXLANBFD {

                key "ID";

                leaf ID {

                    type base:Basetype_UnsignedInteger32;

                }

                leaf Enable {

                    type base:Basetype_Boolean;

                }

                leaf DMAC {

                    type base:Basetype_MacAddress;

                }

                leaf MinRx {

                    type base:Basetype_UnsignedInteger32;

                }

                leaf MinTx {

                    type base:Basetype_UnsignedInteger32;

                }

            }

        }

        container GREP2MPTemplates {

            list GREP2MPTemplate {

                description "This table contains GRE P2MP templates.";

                key "TemplateName";

                leaf TemplateName {

                    type base:Basetype_String {

                        length "1..31";

                    }

                    description "GRE P2MP template name.";

                }

            }

        }

        container GREP2MPTemplateMaps {

            list GREP2MPTemplateMap {

                description "This table contains map information of the GRE P2MP template.";

                key "TemplateName VrfIndex BranchNetworkIPAddr BranchNetworkIPAddrMask TunnelDestIPAddr";

                leaf TemplateName {

                    type base:Basetype_String {

                        length "1..31";

                    }

                    description "GRE P2MP template name.";

                }

                leaf VrfIndex {

                    type base:Basetype_NameAndIndexUnion;

                    description "VPN index for a map.";

                }

                leaf BranchNetworkIPAddr {

                    type base:Basetype_Ipv4Address;

                    description "Branch network IP address for a map.";

                }

                leaf BranchNetworkIPAddrMask {

                    type base:Basetype_Ipv4Address;

                    description "Mask of branch network IP address.";

                }

                leaf TunnelDestIPAddr {

                    type union {

                        type base:Basetype_EmptyString;

                        type base:Basetype_Ipv4Address;

                    }

                    description "Tunnel Destination IP address for a map.";

                }

                leaf ChecksumFill {

                    type base:Basetype_Ipv4Address;

                    description "Contents to fill in the checksum field.";

                }

            }

        }

    }

}
