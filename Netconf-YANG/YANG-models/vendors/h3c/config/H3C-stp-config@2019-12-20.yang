module H3C-stp-config {

    namespace "http://www.h3c.com/netconf/config:1.0";

    prefix "stp-config";

    import comware-basetype {

         prefix "base";

    }

    import comware-extension {

         prefix "ext";

    }

    organization "NEW H3C Technologies Co., Ltd.";

    contact "Website: http://www.h3c.com";

    description "The module entities for stp config.";

    revision 2019-12-20 {

        description "Initial revision.";

    }

    container STP {

        container Base {

            description "The global configuration information of STP feature";

            leaf Enable {

                type base:Basetype_Boolean;

                description "Control whether STP is globally enabled.";

            }

            leaf BPDUProtect {

                type base:Basetype_Boolean;

                description "Control whether BPDU-Protect function is enabled.";

            }

            leaf Mode {

                type enumeration {

                    enum 0;

                    enum 2;

                    enum 3;

                    enum 4;

                }

                description "The spanning-tree working modes:

                         0--STP; 2--RSTP; 3--MSTP; 4--PVST;";

            }

            leaf TcProtect {

                type base:Basetype_Boolean;

                description "Control whether or not BPDU-Protect function is enabled.";

            }

            leaf TcThreshold {

                type base:Basetype_UnsignedInteger32 {

                    range "1..255";

                }

                description "The max TCs that will be processed within the TC-protection period.";

            }

            leaf PathCostMethod {

                type enumeration {

                    enum 0;

                    enum 1;

                    enum 2;

                }

                description "The path cost calculation method:

                         0--Leagcy; 1--IEEE 802.1D-1998; 2--IEEE 802.1t;";

            }

            leaf HelloTime {

                type base:Basetype_UnsignedInteger32 {

                    range "1..10";

                }

                description "The intervals in seconds.";

            }

            leaf MaxHops {

                type base:Basetype_UnsignedInteger32 {

                    range "1..40";

                }

                description "The maximum hops.";

            }

            leaf MaxAge {

                type base:Basetype_UnsignedInteger32 {

                    range "6..40";

                }

                description "The maximum message age.";

            }

            leaf ForwardDelay {

                type base:Basetype_UnsignedInteger32 {

                    range "4..30";

                }

                description "The forward delay timer in seconds.";

            }

            leaf TcSnooping {

                type base:Basetype_Boolean;

                description "Control whether TC-snooping function is enabled.";

            }

            leaf DigestSnooping {

                type base:Basetype_Boolean;

                description "Control whether digest-snooping function is enabled.";

            }

        }

        container Region {

            description "The region configuration information of MST";

            leaf Name {

                type base:Basetype_String {

                    length "1..32";

                }

                description "MST region name";

            }

            leaf RevisionLevel {

                type base:Basetype_UnsignedInteger32 {

                    range "0..65535";

                }

                description "The revision level of a MST region configuration";

            }

        }

        container StiVlans {

            description "Allocation of VLANs per STI

                This table supports creating rows.";

            list StiVlan {

                key "StiId";

                leaf StiId {

                    type base:Basetype_UnsignedInteger32 {

                        range "1..4094";

                    }

                    description "The index of a STI";

                }

                leaf VlanList {

                    type base:Basetype_VlanRange;

                    description "The VLANs mapped to a STI";

                }

            }

        }

        container STIs {

            description "Configuration information per STIs

                This table supports creating rows.";

            list STI {

                key "StiId";

                leaf StiId {

                    type base:Basetype_UnsignedInteger32 {

                        range "0..4094";

                    }

                    description "The index of a STI";

                }

                leaf Priority {

                    type base:Basetype_UnsignedInteger32 {

                        range "0..61440";

                    }

                    description "The priority of a STI, which should be zero or a multiple of 4096.";

                }

                leaf RootType {

                    type enumeration {

                        enum 0;

                        enum 1;

                        enum 2;

                    }

                    description "The preferred root type with different priority:

                          0--Normal(not configured); 1--Secondary root; 2--Primary root;";

                }

            }

        }

        container Interfaces {

            description "Configuration information per port";

            list Interface {

                key "IfIndex";

                leaf IfIndex {

                    type base:Basetype_NameAndIndexUnion;

                    description "The index of a Interface";

                }

                leaf Enable {

                    type base:Basetype_Boolean;

                    description "Control whether STP is enabled on the port.";

                }

                leaf EdgedPort {

                    type base:Basetype_Boolean;

                    description "Control whether a port is edged-port.";

                }

                leaf PointToPoint {

                    type enumeration {

                        enum 1;

                        enum 2;

                        enum 3;

                    }

                    description "Control the point-to-point status of a port:

                         1--Force-true; 2--Force-false; 3--Auto-negotiated by the link;";

                }

                leaf RootProtect {

                    type base:Basetype_Boolean;

                    description "Control whether the root-protection function is enabled";

                }

                leaf LoopProtect {

                    type base:Basetype_Boolean;

                    description "Control whether the loop-protection function is enabled";

                }

                leaf RoleRestrict {

                    type base:Basetype_Boolean;

                    description "Control whether the role-restriction function is enabled";

                }

                leaf TcRestrict {

                    type base:Basetype_Boolean;

                    description "Control whether the TC-restriction function is enabled";

                }

                leaf DigestSnooping {

                    type base:Basetype_Boolean;

                    description "Control whether the digest-snooping function is enabled";

                }

                leaf TransmitHoldCount {

                    type base:Basetype_UnsignedInteger32 {

                        range "1..255";

                    }

                    description "The transmit hold count on an interface";

                }

            }

        }

        container StiInterfaces {

            description "Configuration information per STIs on an interface

                This table supports creating rows.";

            list StiInterface {

                key "StiId IfIndex";

                leaf StiId {

                    type base:Basetype_UnsignedInteger32 {

                        range "0..4094";

                    }

                    description "The index of a STI";

                }

                leaf IfIndex {

                    type base:Basetype_NameAndIndexUnion;

                    description "The index of an Interface";

                }

                leaf Priority {

                    type base:Basetype_UnsignedInteger32 {

                        range "0..240";

                    }

                    description "The port-priority of a STI, which should be zero or a multiple of 16.";

                }

                leaf PathCost {

                    type base:Basetype_UnsignedInteger32 {

                        range "0..200000000";

                    }

                    description "The path cost configuration of a STI on a port, the actual max value of which is

                           different according to the cost calculation method configured at present.

                           Leagcy:      0-200000;

                           802.1D-1998: 0-65535;

                           802.1t:      0-200000000";

                }

            }

        }

        container VLANs {

            description "Configuration information per VLANs for PVST

                This table supports creating rows.";

            list VLAN {

                key "VlanId";

                leaf VlanId {

                    type base:Basetype_UnsignedInteger32 {

                        range "1..4094";

                    }

                    description "The index of a VLAN";

                }

                leaf Enable {

                    type base:Basetype_Boolean;

                    description "Control whether PVST is enabled on the VLAN.";

                }

                leaf Priority {

                    type base:Basetype_UnsignedInteger32 {

                        range "0..61440";

                    }

                    description "The priority of a VLAN, which should be zero or a multiple of 4096.";

                }

                leaf RootType {

                    type enumeration {

                        enum 0;

                        enum 1;

                        enum 2;

                    }

                    description "The preferred root type with different priority:

                          0--Normal(not configured); 1--Secondary root; 2--Primary root;";

                }

                container BridgeTimes {

                    description "Topology change informations per spanning-tree,including HelloTime, 

                          MaxAge, ForwardDelay.";

                    leaf HelloTime {

                        type base:Basetype_UnsignedInteger32 {

                            range "1..10";

                        }

                        description "The hello intervals of the bridge in seconds.";

                    }

                    leaf MaxAge {

                        type base:Basetype_UnsignedInteger32 {

                            range "6..40";

                        }

                        description "The maximum message age of the bridge.";

                    }

                    leaf ForwardDelay {

                        type base:Basetype_UnsignedInteger32 {

                            range "4..30";

                        }

                        description "The forward delay time of the bridge in seconds.";

                    }

                }

            }

        }

        container VlanInterfaces {

            description "Configuration information per VLAN on an interface for PVST

                This table supports creating rows.";

            list VlanInterface {

                key "VlanId IfIndex";

                leaf VlanId {

                    type base:Basetype_UnsignedInteger32 {

                        range "1..4094";

                    }

                    description "The index of a VLAN";

                }

                leaf IfIndex {

                    type base:Basetype_NameAndIndexUnion;

                    description "The index of an Interface";

                }

                leaf Priority {

                    type base:Basetype_UnsignedInteger32 {

                        range "0..240";

                    }

                    description "The port-priority of a VLAN, which should be zero or a multiple of 16.";

                }

                leaf PathCost {

                    type base:Basetype_UnsignedInteger32 {

                        range "0..200000000";

                    }

                    description "The path cost configuration of a VLAN on a port, the actual max value of which is 

                           different according to the cost calculation method configured at present.

                           Leagcy:      0-200000; 

                           802.1D-1998: 0-65535; 

                           802.1t:      0-200000000";

                }

            }

        }

    }

}
