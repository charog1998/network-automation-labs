module H3C-dot1x-config {

    namespace "http://www.h3c.com/netconf/config:1.0";

    prefix "dot1x-config";

    import comware-basetype {

         prefix "base";

    }

    import comware-extension {

         prefix "ext";

    }

    organization "NEW H3C Technologies Co., Ltd.";

    contact "Website: http://www.h3c.com";

    description "The module entities for dot1x config.";

    revision 2019-12-20 {

        description "Initial revision.";

    }

    container Dot1X {

        container Protocol {

            description "Dot1x protocol related paramenters";

            leaf Enable {

                type base:Basetype_Boolean;

                description "This element controls, on the local system, whether or not Dot1x is enabled.";

            }

            leaf AuthenMethod {

                type enumeration {

                    enum 1;

                    enum 2;

                    enum 3;

                }

                description "The Authentication Method of 802.1x:

                         1--Chap; 2--PAP; 3--EAP;";

            }

            leaf DomainDelimiterAt {

                type base:Basetype_Boolean;

                description "indicate whether there is delimiter @ between username and domain.";

            }

            leaf DomainDelimiterSlash {

                type base:Basetype_Boolean;

                description "indicate whether there is delimiter / between username and domain.";

            }

            leaf DomainDelimiterBackSlash {

                type base:Basetype_Boolean;

                description "indicate whether there is delimiter \ between username and domain.";

            }

            leaf DomainDelimiterDot {

                type base:Basetype_Boolean;

                description "indicate whether there is delimiter . between username and domain.";

            }

            leaf QuietEnable {

                type base:Basetype_Boolean;

                description "whether Dot1X is globally queit.";

            }

            leaf QuietInterval {

                type base:Basetype_UnsignedInteger32 {

                    range "10..120";

                }

                description "Period value of Quiet timer";

            }

            leaf HandshakeInterval {

                type base:Basetype_UnsignedInteger32 {

                    range "5..1024";

                }

                description "Period value of handshake timer";

            }

            leaf ReauthenInterval {

                type base:Basetype_UnsignedInteger32 {

                    range "60..7200";

                }

                description "Period value of re-authentication timer";

            }

            leaf ServerInterval {

                type base:Basetype_UnsignedInteger32 {

                    range "100..300";

                }

                description "Period value of server response timer";

            }

            leaf SupplicantInterval {

                type base:Basetype_UnsignedInteger32 {

                    range "1..120";

                }

                description "Period value of supplicant response timer(response /ID exclusively)";

            }

            leaf ReqIDInterval {

                type base:Basetype_UnsignedInteger32 {

                    range "1..120";

                }

                description "Period value of supplicant response/ID timer";

            }

            leaf RequestRetryCount {

                type base:Basetype_UnsignedInteger32 {

                    range "1..10";

                }

                description "The Max count of retrying to send out dot1X’s packets";

            }

        }

        container EAD {

            description "Dot1 EAD feature table";

            leaf AssistEnable {

                type base:Basetype_Boolean;

                description "This element indicates whether Ead assistance is enabled.";

            }

            leaf AssistURL {

                type base:Basetype_String {

                    length "1..64";

                }

                description "URL used in Ead assistance feature";

            }

        }

        container EADFreeIPs {

            description "Dot1 EAD assistant free IP table

                This table supports creating rows.";

            list FreeIP {

                key "IPv4Address IPv4Mask";

                leaf IPv4Address {

                    type base:Basetype_Ipv4Address;

                    description "IP address used in EAD assistance feature";

                }

                leaf IPv4Mask {

                    type base:Basetype_String;

                    description "IP address mask.";

                }

            }

        }

        container Interfaces {

            description "Dot1X interface's information";

            list Interface {

                key "IfIndex";

                leaf IfIndex {

                    type base:Basetype_NameAndIndexUnion;

                    description "The index of a Interface";

                }

                leaf Enable {

                    type base:Basetype_Boolean;

                    description "Indicate whether Dot1X is enabled on a port.";

                }

                leaf SmartonEnable {

                    type base:Basetype_Boolean;

                    description "Enable Status of Smarton feature.";

                }

                leaf PortControl {

                    type enumeration {

                        enum 1;

                        enum 2;

                        enum 3;

                    }

                    description "Portcontrol status of the interface:

                         1--forced-authorized; 2--forced-unauthorized; 3--auto;";

                }

                leaf PortMethod {

                    type enumeration {

                        enum 1;

                        enum 2;

                    }

                    description "Dot1X Control Method of the interface:

                         1--Portbased; 2--MACbased;";

                }

                leaf ReauthenEnable {

                    type base:Basetype_Boolean;

                    description "Indicate whether re-authentication is enabled on this interface.";

                }

                leaf MulticastTrigger {

                    type base:Basetype_Boolean;

                    description "Indicate whether the status of sending multicast request/ID packets is enabled.";

                }

                leaf UnicastTrigger {

                    type base:Basetype_Boolean;

                    description "Indicate whether the status of sending unicast request/ID packets is enabled.";

                }

                leaf HandshakeEnable {

                    type base:Basetype_Boolean;

                    description "Indicate whether handshake feature is enabled on this interface.";

                }

                leaf SecHandshakeEnable {

                    type base:Basetype_Boolean;

                    description "Indicate whether secure handshake feature is enabled on this interface.";

                }

                leaf ReauthUnreachableMode {

                    type enumeration {

                        enum 0;

                        enum 1;

                    }

                    description "Status of user online or offline when the AAA server is not available during re-authenticating:

                         0--Offline; 1--Online;";

                }

                leaf MandDomain {

                    type base:Basetype_String {

                        length "1..255";

                    }

                    description "Mandatory Domain set on this interface";

                }

                leaf MaxUser {

                    type base:Basetype_UnsignedInteger32;

                    description "Maximum user count on this interface";

                }

                leaf FailVLAN {

                    type base:Basetype_UnsignedInteger32 {

                        range "1..4094";

                    }

                    description "VLAN for authentication failure users on the interface";

                }

                leaf CriticalVLAN {

                    type base:Basetype_UnsignedInteger32 {

                        range "1..4094";

                    }

                    description "VLAN for server unavailable situation on the interface";

                }

                leaf GuestVLAN {

                    type base:Basetype_UnsignedInteger32 {

                        range "1..4094";

                    }

                    description "VLAN for unauthenticated users on the interface";

                }

            }

        }

        container Smarton {

            description "Dot1 Smarton feature table";

            leaf SwitchID {

                type base:Basetype_String {

                    length "1..30";

                }

                description "Dot1x smarton switch ID.";

            }

            leaf Password {

                type base:Basetype_String {

                    length "1..16";

                }

                description "Dot1x smarton password.";

            }

            leaf RetryCount {

                type base:Basetype_UnsignedInteger32 {

                    range "1..10";

                }

                description "Maxium attempt count to send out Request packets with smarton notification.";

            }

        }

    }

}
