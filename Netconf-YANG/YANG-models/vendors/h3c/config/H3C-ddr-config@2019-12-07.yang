module H3C-ddr-config {

    namespace "http://www.h3c.com/netconf/config:1.0";

    prefix "ddr-config";

    import comware-basetype {

         prefix "base";

    }

    import comware-extension {

         prefix "ext";

    }

    organization "NEW H3C Technologies Co., Ltd.";

    contact "Website: http://www.h3c.com";

    description "The module entities for ddr config.";

    revision 2019-12-07 {

        description "Initial revision.";

    }

    container DDR {

        container DDRAutodial {

            list Autodial {

                key "IfIndex";

                leaf IfIndex {

                    type base:Basetype_NameAndIndexUnion;

                }

                leaf Time {

                    type base:Basetype_UnsignedInteger32 {

                        range "1..604800";

                    }

                }

            }

        }

        container DDRIdle {

            list Idle {

                key "IfIndex";

                leaf IfIndex {

                    type base:Basetype_NameAndIndexUnion;

                }

                leaf Time {

                    type base:Basetype_UnsignedInteger32 {

                        range "0..65535";

                    }

                }

                leaf Direct {

                    type enumeration {

                        enum 1;

                        enum 2;

                        enum 3;

                    }

                }

            }

        }

        container Bundle {

            list DiaBundle {

                key "IfIndex";

                leaf IfIndex {

                    type base:Basetype_NameAndIndexUnion;

                }

                leaf Enable {

                    type base:Basetype_Boolean;

                }

            }

        }

        container IfDiaGroup {

            list DiaGroup {

                key "IfIndex";

                leaf IfIndex {

                    type base:Basetype_NameAndIndexUnion;

                }

                leaf Num {

                    type base:Basetype_UnsignedInteger32 {

                        range "1..255";

                    }

                }

            }

        }

        container DiaGroupRule {

            list GroupRule {

                key "GroupNumber IpProtocol";

                leaf GroupNumber {

                    type base:Basetype_UnsignedInteger32 {

                        range "1..255";

                    }

                }

                leaf IpProtocol {

                    type enumeration {

                        enum 0;

                        enum 1;

                    }

                }

                leaf IpPermit {

                    type base:Basetype_Boolean;

                }

                leaf AclNum {

                    type base:Basetype_UnsignedInteger32 {

                        range "2000..3999";

                    }

                }

                leaf AclName {

                    type base:Basetype_String {

                        pattern "[a-zA-Z][^?	

]{0,62}";

                    }

                }

            }

        }

        container DDRCircularEnable {

            list CircularEnable {

                key "IfIndex";

                leaf IfIndex {

                    type base:Basetype_NameAndIndexUnion;

                }

                leaf Enable {

                    type base:Basetype_Boolean;

                }

            }

        }

        container DDRDialNumber {

            list DialNumber {

                key "IfIndex";

                leaf IfIndex {

                    type base:Basetype_NameAndIndexUnion;

                }

                leaf Num {

                    type base:Basetype_String {

                        length "1..30";

                    }

                }

                leaf AutoDial {

                    type enumeration {

                        enum 0;

                        enum 1;

                    }

                }

            }

        }

    }

}
