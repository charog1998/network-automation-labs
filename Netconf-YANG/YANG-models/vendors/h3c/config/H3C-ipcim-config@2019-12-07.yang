module H3C-ipcim-config {

    namespace "http://www.h3c.com/netconf/config:1.0";

    prefix "ipcim-config";

    import comware-basetype {

         prefix "base";

    }

    import comware-extension {

         prefix "ext";

    }

    organization "NEW H3C Technologies Co., Ltd.";

    contact "Website: http://www.h3c.com";

    description "The module entities for ipcim config.";

    revision 2019-12-07 {

        description "Initial revision.";

    }

    container IPCIM {

        container IpSourceBindingInterface {

            list SourceBinding {

                key "IfIndex Ipv4Address MacAddress VLANID";

                leaf IfIndex {

                    type base:Basetype_NameAndIndexUnion;

                }

                leaf Ipv4Address {

                    type base:Basetype_Ipv4Address;

                }

                leaf MacAddress {

                    type base:Basetype_MacAddress;

                }

                leaf VLANID {

                    type base:Basetype_UnsignedInteger32 {

                        range "0..4094";

                    }

                }

            }

        }

        container IpVerifySource {

            list VerifySource {

                key "IfIndex";

                leaf IfIndex {

                    type base:Basetype_NameAndIndexUnion;

                }

                leaf VerifyIpAddress {

                    type base:Basetype_Boolean;

                }

                leaf VerifyMacAddress {

                    type base:Basetype_Boolean;

                }

            }

        }

    }

}
