module H3C-telnet-config {

    namespace "http://www.h3c.com/netconf/config:1.0";

    prefix "telnet-config";

    import comware-basetype {

         prefix "base";

    }

    import comware-extension {

         prefix "ext";

    }

    organization "NEW H3C Technologies Co., Ltd.";

    contact "Website: http://www.h3c.com";

    description "The module entities for telnet config.";

    revision 2019-12-17 {

        description "Initial revision.";

    }

    container TELNET {

        container Server {

            description "TELNET server table.";

            leaf State {

                type base:Basetype_EnableState;

                description "Global TELNET Server feature.";

            }

            leaf Ipv4DSCP {

                type base:Basetype_UnsignedInteger32 {

                    range "0..63";

                }

                description "Set the IPv4 Differentiated Services Codepoint (DSCP) value.";

            }

            leaf Ipv6DSCP {

                type base:Basetype_UnsignedInteger32 {

                    range "0..63";

                }

                description "Set the IPv6 Differentiated Services Codepoint (DSCP) value.";

            }

            leaf Ipv4ACLNum {

                type base:Basetype_UnsignedInteger32 {

                    range "2000..4999";

                }

                description "Specify an IPv4 ACL used to control the TELNET clients' access.";

            }

            leaf Ipv6ACLNum {

                type base:Basetype_UnsignedInteger32 {

                    range "2000..4999";

                }

                description "Specify an IPv6 ACL used to control the TELNET clients' access.";

            }

            leaf Ipv4Port {

                type union {

                    type uint32;

                    type uint32;

                }

                description "Specify the IPv4 TELNET listening port.";

            }

            leaf Ipv6Port {

                type union {

                    type uint32;

                    type uint32;

                }

                description "Specify the IPv6 TELNET listening port.";

            }

        }

    }

}
