module H3C-ldp-config {

    namespace "http://www.h3c.com/netconf/config:1.0";

    prefix "ldp-config";

    import comware-basetype {

         prefix "base";

    }

    import comware-extension {

         prefix "ext";

    }

    organization "NEW H3C Technologies Co., Ltd.";

    contact "Website: http://www.h3c.com";

    description "The module entities for ldp config.";

    revision 2019-12-09 {

        description "Initial revision.";

    }

    container LDP {

        container Base {

            description "This table contains global LDP information.";

            leaf Enable {

                type base:Basetype_Boolean;

                description "Whether LDP feature is enabled globally(BOOL_TRUE == Enabled BOOL_FALSE == Disabled)";

            }

            leaf LSPTrigger {

                type enumeration {

                    enum 1;

                    enum 2;

                }

                description "Egress LSP trigger policy：
                  1：Default policy(default).
                  2：All";

            }

        }

        container Interfaces {

            description "This table contains LDP interface information.";

            list Interface {

                description "Row name";

                key "IfIndex";

                leaf IfIndex {

                    type base:Basetype_NameAndIndexUnion;

                    description "Interface index.Unsigned integer.";

                }

                leaf Enable {

                    type base:Basetype_Boolean;

                    description "Enable LDP for the interface.(BOOL_TRUE == Enabled BOOL_FALSE == Disabled(default))";

                }

            }

        }

    }

}
