module H3C-nd-config {

    namespace "http://www.h3c.com/netconf/config:1.0";

    prefix "nd-config";

    import comware-basetype {

         prefix "base";

    }

    import comware-extension {

         prefix "ext";

    }

    organization "NEW H3C Technologies Co., Ltd.";

    contact "Website: http://www.h3c.com";

    description "The module entities for nd config.";

    revision 2019-12-07 {

        description "Initial revision.";

    }

    container ND {

        container NDTable {

            list NDEntry {

                key "IfIndex Ipv6Address";

                leaf IfIndex {

                    type base:Basetype_NameAndIndexUnion;

                }

                leaf Ipv6Address {

                    type base:Basetype_Ipv6Address;

                }

                leaf MacAddress {

                    type base:Basetype_MacAddress;

                }

                leaf VLANID {

                    type base:Basetype_UnsignedInteger32 {

                        range "1..4094";

                    }

                }

                leaf PortIndex {

                    type base:Basetype_NameAndIndexUnion;

                }

                leaf VrfIndex {

                    type base:Basetype_NameAndIndexUnion;

                }

            }

        }

        container NDLearnLimit {

            list LearnLimit {

                key "IfIndex";

                leaf IfIndex {

                    type base:Basetype_NameAndIndexUnion;

                }

                leaf LearnMaxNum {

                    type base:Basetype_UnsignedInteger32 {

                        range "1..max";

                    }

                }

            }

        }

        container NDInterface {

            list Interface {

                key "IfIndex";

                leaf IfIndex {

                    type base:Basetype_NameAndIndexUnion;

                }

                leaf DADAttempts {

                    type base:Basetype_UnsignedInteger32 {

                        range "0..600";

                    }

                }

                leaf ModeUNI {

                    type base:Basetype_Boolean;

                }

            }

        }

        container NDConfig {

            leaf StaleAging {

                type base:Basetype_UnsignedInteger32 {

                    range "1..1440";

                }

            }

            leaf LinkLocalMinimize {

                type base:Basetype_Boolean;

            }

            leaf HopLimit {

                type base:Basetype_UnsignedInteger32 {

                    range "1..255";

                }

            }

        }

        container NDRA {

            list RA {

                key "IfIndex";

                leaf IfIndex {

                    type base:Basetype_NameAndIndexUnion;

                }

                leaf RAHalt {

                    type base:Basetype_Boolean;

                }

                leaf MaxInterval {

                    type base:Basetype_UnsignedInteger32 {

                        range "4..1800";

                    }

                }

                leaf MinInterval {

                    type base:Basetype_UnsignedInteger32 {

                        range "3..1350";

                    }

                }

                leaf NoAdvLinkMTU {

                    type base:Basetype_Boolean;

                }

                leaf HopLimitUnspecified {

                    type base:Basetype_Boolean;

                }

                leaf ManagedAddressFlag {

                    type base:Basetype_Boolean;

                }

                leaf OtherFlag {

                    type base:Basetype_Boolean;

                }

                leaf RouterLifetime {

                    type base:Basetype_UnsignedInteger32 {

                        range "0..9000";

                    }

                }

                leaf NSRetransTimer {

                    type base:Basetype_UnsignedInteger32 {

                        range "1000..4294967295";

                    }

                }

                leaf RouterPreference {

                    type enumeration {

                        enum 1;

                        enum 2;

                        enum 3;

                    }

                }

                leaf NudReachableTime {

                    type base:Basetype_UnsignedInteger32 {

                        range "1..3600000";

                    }

                }

            }

        }

        container NDRAPrefix {

            list RAPrefix {

                key "IfIndex";

                leaf IfIndex {

                    type base:Basetype_NameAndIndexUnion;

                }

                list Ipv6Prefix {

                    key "Ipv6Address Ipv6PrefixLength";

                    leaf Ipv6Address {

                        type base:Basetype_Ipv6Address;

                    }

                    leaf Ipv6PrefixLength {

                        type base:Basetype_UnsignedInteger32 {

                            range "1..128";

                        }

                    }

                }

                leaf ValidLifetime {

                    type base:Basetype_UnsignedInteger32;

                }

                leaf PreferredLifetime {

                    type base:Basetype_UnsignedInteger32;

                }

                leaf NoAutoConfig {

                    type base:Basetype_Boolean;

                }

                leaf OffLink {

                    type base:Basetype_Boolean;

                }

                leaf NoAdvertise {

                    type base:Basetype_Boolean;

                }

            }

        }

        container NDProxy {

            list Proxy {

                key "IfIndex";

                leaf IfIndex {

                    type base:Basetype_NameAndIndexUnion;

                }

                leaf ProxyEnable {

                    type base:Basetype_Boolean;

                }

                leaf LocalProxyEnable {

                    type base:Basetype_Boolean;

                }

            }

        }

        container NDSrcmacAtkDetec {

            leaf SrcmacMode {

                type enumeration {

                    enum 0;

                    enum 1;

                    enum 2;

                }

            }

            leaf SrcmacThreshold {

                type base:Basetype_UnsignedInteger32 {

                    range "1..5000";

                }

            }

        }

        container NDIfAtkSuppression {

            leaf Enable {

                type base:Basetype_Boolean;

            }

            leaf Threshold {

                type base:Basetype_UnsignedInteger32 {

                    range "1..5000";

                }

            }

        }

        container NDDNSSuppress {

            list DNSSuppress {

                key "IfIndex";

                leaf IfIndex {

                    type base:Basetype_NameAndIndexUnion;

                }

                leaf ServerSuppressEnable {

                    type base:Basetype_Boolean;

                }

                leaf SearchListSuppressEnable {

                    type base:Basetype_Boolean;

                }

            }

        }

        container NDRouteAdvertise {

            list RouteAdvertise {

                key "IfIndex";

                leaf IfIndex {

                    type base:Basetype_NameAndIndexUnion;

                }

                leaf Enable {

                    type base:Basetype_Boolean;

                }

            }

        }

        container NDDNSServer {

            list DNSServer {

                key "IfIndex Ipv6Address";

                leaf IfIndex {

                    type base:Basetype_NameAndIndexUnion;

                }

                leaf Ipv6Address {

                    type base:Basetype_Ipv6Address;

                }

                leaf LifeTime {

                    type base:Basetype_UnsignedInteger32 {

                        range "4..4294967295";

                    }

                }

                leaf Infinite {

                    type base:Basetype_Boolean;

                }

                leaf Sequence {

                    type base:Basetype_UnsignedInteger32 {

                        range "0..4294967295";

                    }

                }

            }

        }

        container NDDNSSearchList {

            list DNSSearchList {

                key "IfIndex DomainName";

                leaf IfIndex {

                    type base:Basetype_NameAndIndexUnion;

                }

                leaf DomainName {

                    type base:Basetype_String {

                        length "1..253";

                    }

                }

                leaf LifeTime {

                    type base:Basetype_UnsignedInteger32 {

                        range "4..4294967295";

                    }

                }

                leaf Infinite {

                    type base:Basetype_Boolean;

                }

                leaf Sequence {

                    type base:Basetype_UnsignedInteger32 {

                        range "0..4294967295";

                    }

                }

            }

        }

    }

}
