module H3C-modem-config {

    namespace "http://www.h3c.com/netconf/config:1.0";

    prefix "modem-config";

    import comware-basetype {

         prefix "base";

    }

    import comware-extension {

         prefix "ext";

    }

    organization "NEW H3C Technologies Co., Ltd.";

    contact "Website: http://www.h3c.com";

    description "The module entities for modem config.";

    revision 2019-12-07 {

        description "Initial revision.";

    }

    container MODEM {

        container ModemEnable {

            list Enable {

                key "IfIndex";

                leaf IfIndex {

                    type base:Basetype_NameAndIndexUnion;

                }

                leaf CallType {

                    type enumeration {

                        enum 1;

                        enum 2;

                        enum 3;

                    }

                }

            }

        }

    }

}
