module H3C-super-config {

    namespace "http://www.h3c.com/netconf/config:1.0";

    prefix "super-config";

    import comware-basetype {

         prefix "base";

    }

    import comware-extension {

         prefix "ext";

    }

    organization "NEW H3C Technologies Co., Ltd.";

    contact "Website: http://www.h3c.com";

    description "The module entities for super config.";

    revision 2019-12-20 {

        description "Initial revision.";

    }

    container Super {

        container GlobalConfig {

            leaf ModeType {

                type base:Basetype_UnsignedInteger32 {

                    range "0..3";

                }

            }

            leaf DefaultRole {

                type base:Basetype_String {

                    length "1..63";

                }

            }

        }

        container Passwords {

            list Password {

                key "RoleName";

                leaf RoleName {

                    type base:Basetype_String {

                        length "1..63";

                    }

                }

                leaf Password {

                    type base:Basetype_String {

                        length "1..63";

                    }

                }

            }

        }

    }

}
