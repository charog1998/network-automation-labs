module H3C-lldp-config {

    namespace "http://www.h3c.com/netconf/config:1.0";

    prefix "lldp-config";

    import comware-basetype {

         prefix "base";

    }

    import comware-extension {

         prefix "ext";

    }

    organization "NEW H3C Technologies Co., Ltd.";

    contact "Website: http://www.h3c.com";

    description "The module entities for lldp config.";

    revision 2019-12-20 {

        description "Initial revision.";

    }

    container LLDP {

        container GlobalStatus {

            description "LLDP global status configuration";

            leaf Enable {

                type base:Basetype_Boolean;

                description "LLDP feature enable status";

            }

            leaf CDP {

                type base:Basetype_Boolean;

                description "CDP compliance status";

            }

            leaf TxInterval {

                type base:Basetype_UnsignedInteger32 {

                    range "5..32768";

                }

                description "Transmit interval of LLDPDU";

            }

            leaf FastInterval {

                type base:Basetype_UnsignedInteger32 {

                    range "1..3600";

                }

                description "Fast transmit interval of LLDPDU";

            }

            leaf ReInitDelay {

                type base:Basetype_UnsignedInteger32 {

                    range "1..10";

                }

                description "Reinitialize delay";

            }

            leaf NofityInterval {

                type base:Basetype_UnsignedInteger32 {

                    range "5..3600";

                }

                description "Traps notify interval";

            }

            leaf Mode {

                type enumeration {

                    enum 0;

                    enum 1;

                }

                description "Bridge mode, Enumeration:

                    0 Customer bridge mode.

                    1 Service bridge mode.";

            }

            leaf MaxCredit {

                type base:Basetype_UnsignedInteger32 {

                    range "1..100";

                }

                description "Token bucket size for sending LLDPDUs";

            }

            leaf HoldMult {

                type base:Basetype_UnsignedInteger32 {

                    range "2..10";

                }

                description "TTL multiplier";

            }

            leaf FastCount {

                type base:Basetype_UnsignedInteger32 {

                    range "1..8";

                }

                description "TTL multiplier";

            }

            leaf RxTimeout {

                type union {

                    type uint32;

                    type uint32;

                }

                description "The timeout for receiving LLDPDUs";

            }

        }

        container Interfaces {

            description "LLDP interface status configuration";

            list Interface {

                description "Row name";

                key "IfIndex";

                leaf IfIndex {

                    type base:Basetype_NameAndIndexUnion;

                    description "Interface index";

                }

                leaf Enable {

                    type base:Basetype_Boolean;

                    description "Protocol interface status";

                }

                leaf CDP {

                    type base:Basetype_Boolean;

                    description "Interface CDP compliance status";

                }

                leaf MEDTopoChange {

                    type base:Basetype_Boolean;

                    description "MED topology change notification status";

                }

            }

        }

        container IfAgents {

            description "LLDP interface agent configuration";

            list IfAgent {

                description "Row name";

                key "IfIndex AgentID";

                leaf IfIndex {

                    type base:Basetype_NameAndIndexUnion;

                    description "Interface index";

                }

                leaf AgentID {

                    type enumeration {

                        enum 1;

                        enum 2;

                        enum 3;

                    }

                    description "LLDP agent ID";

                }

                container AdminStatus {

                    description "Admin status of LLDP";

                    leaf Tx {

                        type base:Basetype_Boolean;

                        description "Transmit status";

                    }

                    leaf Rx {

                        type base:Basetype_Boolean;

                        description "Receive status";

                    }

                }

                leaf CheckChangeInterval {

                    type base:Basetype_UnsignedInteger32 {

                        range "1..30";

                    }

                    description "Check change interval";

                }

                leaf Encap {

                    type enumeration {

                        enum 0;

                        enum 1;

                    }

                    description "LLDPDU Ethernet head encapsulation, Enumeration:

                          0 Ethernet II encapsulation.

                          1 SNAP encapsulation.";

                }

                leaf AddressFormat {

                    type enumeration {

                        enum 0;

                        enum 1;

                    }

                    description "Management address format, Enumeration:

                          0 Number.

                          1 String.";

                }

                leaf RemoteChange {

                    type base:Basetype_Boolean;

                    description "Remote change notification status";

                }

            }

        }

        container TLVSelects {

            description "LLDP interface TLV transmitting status configuration";

            list TLV {

                description "Row name";

                key "IfIndex AgentID";

                leaf IfIndex {

                    type base:Basetype_NameAndIndexUnion;

                    description "Interface index";

                }

                leaf AgentID {

                    type enumeration {

                        enum 1;

                        enum 2;

                        enum 3;

                    }

                    description "LLDP agent ID";

                }

                leaf PortDesc {

                    type base:Basetype_Boolean;

                    description "Port description TLV transmitting status";

                }

                leaf SysName {

                    type base:Basetype_Boolean;

                    description "System name TLV transmitting status";

                }

                leaf SysDesc {

                    type base:Basetype_Boolean;

                    description "System description TLV transmitting status";

                }

                leaf SysCap {

                    type base:Basetype_Boolean;

                    description "System capability TLV transmitting status";

                }

                container ManageAddress {

                    description "Management address TLV transmitting configuration";

                    leaf SubType {

                        type enumeration {

                            enum 1;

                            enum 2;

                        }

                        description "Management address sub type, Enumeration:

                                1 Ipv4.

                                2 Ipv6.";

                    }

                    leaf Address {

                        type base:Basetype_Binary {

                            length "1..31";

                        }

                        description "Management address value, Base64 Binary. 

                                Length: 1 to 31 octets.

                                The format of data is determined by the address subtype.";

                    }

                    leaf Enable {

                        type base:Basetype_Boolean;

                        description "Management address TLV transmitting status";

                    }

                }

                leaf PVID {

                    type base:Basetype_Boolean;

                    description "Port VLAN ID TLV transmitting status";

                }

                container ProtocolVLAN {

                    description "Port and protocol VLAN ID TLV transmitting configuration";

                    leaf VLANID {

                        type base:Basetype_UnsignedInteger32 {

                            range "1..4094";

                        }

                        description "Protocol VLAN ID.";

                    }

                    leaf Enable {

                        type base:Basetype_Boolean;

                        description "Port and protocol VLAN ID TLV transmitting status";

                    }

                }

                container VLANName {

                    description "VLAN name TLV transmitting configuration";

                    leaf VLANID {

                        type base:Basetype_UnsignedInteger32 {

                            range "1..4094";

                        }

                        description "VLAN ID";

                    }

                    leaf Enable {

                        type base:Basetype_Boolean;

                        description "VLAN name TLV transmitting status";

                    }

                }

                leaf DCBX {

                    type base:Basetype_Boolean;

                    description "DCBX TLV transmitting status";

                }

                leaf LinkAgg {

                    type base:Basetype_Boolean;

                    description "Link aggregation TLV transmitting status";

                }

                container ManageVLAN {

                    description "Management VLAN TLV transmitting configuration";

                    leaf VLANID {

                        type base:Basetype_UnsignedInteger32 {

                            range "1..4094";

                        }

                        description "VLAN ID";

                    }

                    leaf Enable {

                        type base:Basetype_Boolean;

                        description "Management VLAN TLV transmitting status";

                    }

                }

                leaf EVB {

                    type base:Basetype_Boolean;

                    description "EVB TLV transmitting status";

                }

                leaf QCN {

                    type base:Basetype_Boolean;

                    description "QCN TLV transmitting status";

                }

                leaf MACPHY {

                    type base:Basetype_Boolean;

                    description "Mac physic configuration/status TLV transmitting status";

                }

                leaf Power {

                    type base:Basetype_Boolean;

                    description "Power via MDI TLV transmitting status";

                }

                leaf MaxFrame {

                    type base:Basetype_Boolean;

                    description "Max frame size TLV transmitting status";

                }

                leaf MEDCapability {

                    type base:Basetype_Boolean;

                    description "MED capability TLV transmitting status";

                }

                leaf NetworkPolicy {

                    type base:Basetype_Boolean;

                    description "Network policy TLV transmitting status";

                }

                leaf ExtPower {

                    type base:Basetype_Boolean;

                    description "Extended power via MDI TLV transmitting status";

                }

                leaf Inventory {

                    type base:Basetype_Boolean;

                    description "Inventory TLVs transmitting status";

                }

            }

        }

        container ELINumbers {

            description "LLDP emergency location identification number configuration";

            list ELIN {

                description "Row name";

                key "IfIndex";

                leaf IfIndex {

                    type base:Basetype_NameAndIndexUnion;

                    description "Interface index";

                }

                leaf ELINumber {

                    type base:Basetype_String {

                        pattern "[0-9]{10,25}";

                    }

                    description "Emergency Location Identification Number";

                }

                leaf Enable {

                    type base:Basetype_Boolean;

                    description "Location ID TLV transmitting status";

                }

            }

        }

        container CivicAddresses {

            description "LLDP civic address configuration";

            list CivicAddress {

                description "Row name";

                key "IfIndex";

                leaf IfIndex {

                    type base:Basetype_NameAndIndexUnion;

                    description "Interface index";

                }

                leaf DeviceType {

                    type enumeration {

                        enum 0;

                        enum 1;

                        enum 2;

                    }

                    description "Device type, Enumeration:

                          0 DHCP Server.

                          1 Network device.

                          2 MED endpoint.";

                }

                leaf CountryCode {

                    type base:Basetype_String {

                        pattern "[A-Z]{2,2}";

                    }

                    description "Country code";

                }

                list CA {

                    description "Civic address";

                    key "Type Value";

                    leaf Type {

                        type base:Basetype_UnsignedInteger32 {

                            range "0..255";

                        }

                        description "Civic address type, Value range: 0 to 255.";

                    }

                    leaf Value {

                        type base:Basetype_OctectString {

                            length "1..250";

                        }

                        description "Civic address value";

                    }

                }

                leaf Enable {

                    type base:Basetype_Boolean;

                    description "Location ID TLV transmitting status";

                }

            }

        }

    }

}
