module H3C-identity-config {

    namespace "http://www.h3c.com/netconf/config:1.0";

    prefix "identity-config";

    import comware-basetype {

         prefix "base";

    }

    import comware-extension {

         prefix "ext";

    }

    organization "NEW H3C Technologies Co., Ltd.";

    contact "Website: http://www.h3c.com";

    description "The module entities for identity config.";

    revision 2019-12-20 {

        description "Initial revision.";

    }

    container Identity {

        container Policies {

            container RestfulPolicies {

                list RestfulPolicy {

                    key "PolicyName RestfulServerName";

                    leaf PolicyName {

                        type base:Basetype_String {

                            length "1..31";

                        }

                    }

                    leaf RestfulServerName {

                        type base:Basetype_String {

                            length "1..31";

                        }

                    }

                }

            }

            container LDAPPolicies {

                list LDAPPolicy {

                    key "PolicyName LDAPSchemeName";

                    leaf PolicyName {

                        type base:Basetype_String {

                            length "1..31";

                        }

                    }

                    leaf LDAPSchemeName {

                        type base:Basetype_String {

                            length "1..32";

                        }

                    }

                }

            }

        }

        container IdentityEnable {

            leaf Enable {

                type base:Basetype_Boolean;

            }

        }

        container StaticUsers {

            list StaticUser {

                key "DomainName Name IpType IpAddress MacAddress";

                leaf DomainName {

                    type union {

                        type base:Basetype_EmptyString;

                        type base:Basetype_String {

                            length "1..255";

                        }

                    }

                }

                leaf Name {

                    type base:Basetype_String {

                        length "1..55";

                    }

                }

                leaf IpType {

                    type base:Basetype_UnsignedInteger32 {

                        range "0..1";

                    }

                }

                leaf IpAddress {

                    type base:Basetype_IpAddress;

                }

                leaf MacAddress {

                    type union {

                        type base:Basetype_EmptyString;

                        type base:Basetype_MacAddress;

                    }

                }

            }

        }

        container OnlineUsers {

            list OnlineUser {

                key "DomainName UserName IpAddress MacAddress Position";

                leaf DomainName {

                    type union {

                        type base:Basetype_EmptyString;

                        type base:Basetype_String {

                            length "1..255";

                        }

                    }

                }

                leaf UserName {

                    type base:Basetype_String {

                        length "1..55";

                    }

                }

                leaf IpAddress {

                    type base:Basetype_IpAddress;

                }

                leaf MacAddress {

                    type base:Basetype_MacAddress;

                }

                leaf Position {

                    type base:Basetype_UnsignedInteger32 {

                        range "0..4294967295";

                    }

                }

                leaf Type {

                    type base:Basetype_UnsignedInteger32 {

                        range "0..1";

                    }

                }

            }

        }

        container DownloadOnlineUser {

            list OnlineUser {

                key "domain userName vpnName userIp macAddr Position";

                leaf domain {

                    type union {

                        type base:Basetype_EmptyString;

                        type base:Basetype_String {

                            length "1..255";

                        }

                    }

                }

                leaf userName {

                    type base:Basetype_String {

                        length "1..55";

                    }

                }

                leaf vpnName {

                    type union {

                        type base:Basetype_EmptyString;

                        type base:Basetype_String {

                            length "1..31";

                        }

                    }

                }

                leaf userIp {

                    type base:Basetype_IpAddress;

                }

                leaf macAddr {

                    type union {

                        type base:Basetype_EmptyString;

                        type base:Basetype_MacAddress;

                    }

                }

                leaf Position {

                    type base:Basetype_UnsignedInteger32 {

                        range "0..4294967295";

                    }

                }

            }

        }

        container DownloadOfflineUser {

            list OfflineUser {

                key "domain userName vpnName userIp macAddr";

                leaf domain {

                    type union {

                        type base:Basetype_EmptyString;

                        type base:Basetype_String {

                            length "1..255";

                        }

                    }

                }

                leaf userName {

                    type base:Basetype_String {

                        length "1..55";

                    }

                }

                leaf vpnName {

                    type union {

                        type base:Basetype_EmptyString;

                        type base:Basetype_String {

                            length "1..31";

                        }

                    }

                }

                leaf userIp {

                    type base:Basetype_IpAddress;

                }

                leaf macAddr {

                    type union {

                        type base:Basetype_EmptyString;

                        type base:Basetype_MacAddress;

                    }

                }

            }

        }

        container RestfulServers {

            list RestfulServer {

                key "ServerName";

                leaf ServerName {

                    type base:Basetype_String {

                        length "1..31";

                    }

                }

                leaf LoginName {

                    type union {

                        type base:Basetype_EmptyString;

                        type base:Basetype_String {

                            length "1..55";

                        }

                    }

                }

                leaf Password {

                    type union {

                        type base:Basetype_EmptyString;

                        type base:Basetype_String {

                            length "1..63";

                        }

                    }

                }

                leaf PasswordHide {

                    type base:Basetype_String {

                        length "1..255";

                    }

                }

                leaf VpnName {

                    type union {

                        type base:Basetype_EmptyString;

                        type base:Basetype_String {

                            length "1..31";

                        }

                    }

                }

                leaf GetUserDatabase {

                    type union {

                        type base:Basetype_EmptyString;

                        type base:Basetype_OctectString {

                            length "1..255";

                        }

                    }

                }

                leaf GetUserGroupDatabase {

                    type union {

                        type base:Basetype_EmptyString;

                        type base:Basetype_OctectString {

                            length "1..255";

                        }

                    }

                }

                leaf GetOnlineUser {

                    type union {

                        type base:Basetype_EmptyString;

                        type base:Basetype_OctectString {

                            length "1..255";

                        }

                    }

                }

                leaf PutOnlineUser {

                    type union {

                        type base:Basetype_EmptyString;

                        type base:Basetype_OctectString {

                            length "1..255";

                        }

                    }

                }

                leaf PutOfflineUser {

                    type union {

                        type base:Basetype_EmptyString;

                        type base:Basetype_OctectString {

                            length "1..255";

                        }

                    }

                }

                leaf DetectEnable {

                    type base:Basetype_Boolean;

                }

                leaf DetectInterval {

                    type base:Basetype_UnsignedInteger32 {

                        range "1..10";

                    }

                }

                leaf DetectMaxCount {

                    type base:Basetype_UnsignedInteger32 {

                        range "1..5";

                    }

                }

            }

        }

        container UserImportPolicies {

            list UserImportPolicy {

                key "PolicyName";

                leaf PolicyName {

                    type base:Basetype_String {

                        length "1..31";

                    }

                }

                leaf UpdateInterval {

                    type base:Basetype_UnsignedInteger32 {

                        range "1..65536";

                    }

                }

                leaf ImportType {

                    type base:Basetype_UnsignedInteger32 {

                        range "1..3";

                    }

                }

            }

        }

        container UserAccountsAutoImport {

            list UserAccountAutoImport {

                key "PolicyName";

                leaf PolicyName {

                    type base:Basetype_String {

                        length "1..31";

                    }

                }

                leaf Auto {

                    type base:Basetype_Boolean;

                }

            }

        }

        container OnlineUserDomFormat {

            leaf DomainFormat {

                type base:Basetype_UnsignedInteger32 {

                    range "1..3";

                }

            }

        }

        container SecManageServers {

            list SecManageServer {

                key "ServerName";

                leaf ServerName {

                    type base:Basetype_String {

                        length "1..31";

                    }

                }

                leaf ListenPort {

                    type union {

                        type base:Basetype_EmptyString;

                        type base:Basetype_UnsignedInteger32 {

                            range "1..65535";

                        }

                    }

                }

                leaf EncrypAlgorithm {

                    type union {

                        type base:Basetype_EmptyString;

                        type base:Basetype_UnsignedInteger32 {

                            range "0..1";

                        }

                    }

                }

                leaf SharedKey {

                    type union {

                        type base:Basetype_EmptyString;

                        type base:Basetype_String {

                            length "1..63";

                        }

                    }

                }

                leaf SharedKeyHide {

                    type base:Basetype_String {

                        length "1..255";

                    }

                }

            }

        }

        container SecManageIPs {

            list SecManageIP {

                key "ServerName Ipv4Address";

                leaf ServerName {

                    type base:Basetype_String {

                        length "1..31";

                    }

                }

                leaf Ipv4Address {

                    type base:Basetype_Ipv4Address;

                }

            }

        }

    }

}
