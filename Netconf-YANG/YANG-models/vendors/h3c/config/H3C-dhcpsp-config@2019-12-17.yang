module H3C-dhcpsp-config {

    namespace "http://www.h3c.com/netconf/config:1.0";

    prefix "dhcpsp-config";

    import comware-basetype {

         prefix "base";

    }

    import comware-extension {

         prefix "ext";

    }

    organization "NEW H3C Technologies Co., Ltd.";

    contact "Website: http://www.h3c.com";

    description "The module entities for dhcpsp config.";

    revision 2019-12-17 {

        description "Initial revision.";

    }

    container DHCPSP {

        container DHCPSPBindingDatabase {

            leaf FileName {

                type base:Basetype_String {

                    length "1..255";

                }

            }

            leaf URL {

                type base:Basetype_String {

                    length "1..255";

                }

            }

            leaf Username {

                type base:Basetype_String {

                    length "1..32";

                }

            }

            leaf Password {

                type base:Basetype_String {

                    length "1..32";

                }

            }

            leaf UpdateInterval {

                type base:Basetype_UnsignedInteger32 {

                    range "60..864000";

                }

            }

        }

        container DHCPSPInterface {

            list Interface {

                key "IfIndex";

                leaf IfIndex {

                    type base:Basetype_NameAndIndexUnion;

                }

                leaf BindingRecord {

                    type base:Basetype_Boolean;

                }

                leaf CheckMacAddress {

                    type base:Basetype_Boolean;

                }

                leaf CheckRequestMessage {

                    type base:Basetype_Boolean;

                }

                leaf Trust {

                    type base:Basetype_Boolean;

                }

                leaf LearnMaxNum {

                    type base:Basetype_UnsignedInteger32;

                }

                leaf RateLimitNum {

                    type base:Basetype_UnsignedInteger32;

                }

            }

        }

        container DHCPSPOpt82CircuitIDVLAN {

            list VLANCircuitID {

                key "IfIndex VLANID";

                leaf IfIndex {

                    type base:Basetype_NameAndIndexUnion;

                }

                leaf VLANID {

                    type base:Basetype_UnsignedInteger32 {

                        range "1..4094";

                    }

                }

                leaf CircuitID {

                    type base:Basetype_String {

                        length "3..63";

                    }

                }

            }

        }

        container DHCPSPOpt82RemoteIDVLAN {

            list VLANRemoteID {

                key "IfIndex VLANID";

                leaf IfIndex {

                    type base:Basetype_NameAndIndexUnion;

                }

                leaf VLANID {

                    type base:Basetype_UnsignedInteger32 {

                        range "1..4094";

                    }

                }

                leaf RemoteID {

                    type base:Basetype_String {

                        length "1..63";

                    }

                }

                leaf Sysname {

                    type base:Basetype_Boolean;

                }

            }

        }

        container DHCPSPOpt82 {

            list Option82 {

                key "IfIndex";

                leaf IfIndex {

                    type base:Basetype_NameAndIndexUnion;

                }

                leaf Option82Enable {

                    type base:Basetype_Boolean;

                }

                leaf Strategy {

                    type enumeration {

                        enum 0;

                        enum 1;

                        enum 2;

                    }

                }

                container Circuit {

                    leaf CircuitID {

                        type base:Basetype_String {

                            length "3..63";

                        }

                    }

                    leaf CircuitIDMode {

                        type enumeration {

                            enum 0;

                            enum 1;

                            enum 2;

                        }

                    }

                    leaf CircuitIDNodeIDType {

                        type enumeration {

                            enum 0;

                            enum 1;

                            enum 2;

                        }

                    }

                    leaf CircuitIDNodeID {

                        type base:Basetype_String {

                            length "1..50";

                        }

                    }

                    leaf CircuitIDFormat {

                        type enumeration {

                            enum 0;

                            enum 1;

                            enum 2;

                        }

                    }

                }

                container Remote {

                    leaf RemoteIDMode {

                        type enumeration {

                            enum 0;

                            enum 1;

                            enum 2;

                        }

                    }

                    leaf RemoteID {

                        type base:Basetype_String {

                            length "1..63";

                        }

                    }

                    leaf RemoteIDFormat {

                        type enumeration {

                            enum 0;

                            enum 1;

                        }

                    }

                }

            }

        }

        container DHCPSPConfig {

            leaf DHCPSPEnable {

                type base:Basetype_Boolean;

            }

        }

    }

}
