module H3C-mac-config {

    namespace "http://www.h3c.com/netconf/config:1.0";

    prefix "mac-config";

    import comware-basetype {

         prefix "base";

    }

    import comware-extension {

         prefix "ext";

    }

    organization "NEW H3C Technologies Co., Ltd.";

    contact "Website: http://www.h3c.com";

    description "The module entities for mac config.";

    revision 2019-12-07 {

        description "Initial revision.";

    }

    container MAC {

        container MacUnicastTable {

            list Unicast {

                key "VLANID MacAddress";

                leaf VLANID {

                    type base:Basetype_UnsignedInteger32 {

                        range "1..4094";

                    }

                }

                leaf MacAddress {

                    type base:Basetype_MacAddress;

                }

                leaf PortIndex {

                    type base:Basetype_NameAndIndexUnion;

                }

                leaf Status {

                    type enumeration {

                        enum 2;

                        enum 3;

                        enum 4;

                    }

                }

            }

        }

        container MacGroupTable {

            list Group {

                key "VLANID MacAddress";

                leaf VLANID {

                    type base:Basetype_UnsignedInteger32 {

                        range "1..4094";

                    }

                }

                leaf MacAddress {

                    type base:Basetype_MacAddress;

                }

                leaf Status {

                    type enumeration {

                        enum 5;

                        enum 6;

                    }

                }

                leaf PortList {

                    type base:Basetype_PortList;

                }

            }

        }

        container MacAging {

            leaf AgingTime {

                type base:Basetype_UnsignedInteger32;

            }

        }

        container MacPort {

            list PortLearn {

                key "PortIndex";

                leaf PortIndex {

                    type base:Basetype_NameAndIndexUnion;

                }

                leaf LearnEnable {

                    type base:Basetype_Boolean;

                }

                leaf LearnMaxNum {

                    type base:Basetype_UnsignedInteger32 {

                        range "0..65535";

                    }

                }

                leaf PortForwardingEnable {

                    type base:Basetype_Boolean;

                }

            }

        }

        container MacVLAN {

            list VLANLearn {

                key "VLANID";

                leaf VLANID {

                    type base:Basetype_UnsignedInteger32 {

                        range "1..4094";

                    }

                }

                leaf LearnEnable {

                    type base:Basetype_Boolean;

                }

                leaf LearnMaxNum {

                    type base:Basetype_UnsignedInteger32 {

                        range "0..65535";

                    }

                }

                leaf VLANForwardingEnable {

                    type base:Basetype_Boolean;

                }

            }

        }

        container MacFwdSrcCheck {

            list FwdSrcCheck {

                key "IfIndex";

                leaf IfIndex {

                    type base:Basetype_NameAndIndexUnion;

                }

                leaf FwdSrcCheckEnable {

                    type base:Basetype_Boolean;

                }

            }

        }

    }

}
