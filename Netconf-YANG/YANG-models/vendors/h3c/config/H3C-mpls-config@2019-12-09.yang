module H3C-mpls-config {

    namespace "http://www.h3c.com/netconf/config:1.0";

    prefix "mpls-config";

    import comware-basetype {

         prefix "base";

    }

    import comware-extension {

         prefix "ext";

    }

    organization "NEW H3C Technologies Co., Ltd.";

    contact "Website: http://www.h3c.com";

    description "The module entities for mpls config.";

    revision 2019-12-09 {

        description "Synchronize the modification of the schema file to the YANG file.";

    }

    revision 2018-05-10 {

        description "Initial revision.";

    }

    container MPLS {

        container Base {

            description "MPLS base table";

            leaf LSRID {

                type base:Basetype_Ipv4Address;

                description "LSRID";

            }

            leaf CBTSStatInterval {

                type base:Basetype_UnsignedShort;

                description "CBTS Statistics Interval Times";

            }

            leaf MPLSBFD {

                type base:Basetype_Boolean;

                description "Mpls bfd enable";

            }

        }

        container Interfaces {

            description "This table contains MPLS interface information.";

            list Interface {

                description "Interface row name";

                key "IfIndex";

                leaf IfIndex {

                    type base:Basetype_NameAndIndexUnion;

                    description "Index column IfIndex NameAndIndexUnion";

                }

                leaf Enable {

                    type base:Basetype_Boolean;

                    description "Enable MPLS";

                }

            }

        }

        container TunnelPolicies {

            description "This table contains Tunnel policy information

                This table supports creating rows.";

            list TunnelPolicy {

                key "PolicyName";

                leaf PolicyName {

                    type base:Basetype_String {

                        length "1..19";

                    }

                    description "Name of tunnel policy";

                }

                leaf Default {

                    type base:Basetype_Boolean;

                    description "BOOL_TRUE == enable BOOL_FALSE == unenable";

                }

                container Sequence {

                    description "";

                    leaf Strict {

                        type base:Basetype_Boolean;

                        description "BOOL_TRUE == enable BOOL_FALSE == unenable";

                    }

                    leaf-list PrefLspType {

                        type enumeration {

                            enum 0;

                            enum 1;

                            enum 2;

                            enum 3;

                        }

                        description "PrefLspType status";

                    }

                    leaf LoadBalancingNum {

                        type base:Basetype_UnsignedInteger32 {

                            range "1..4294967295";

                        }

                        description "Load balancing number";

                    }

                }

            }

        }

        container PreferredTunnelPolicies {

            description "This table contains Tunnel policy information

                This table supports creating rows.";

            list PreferredTunnelPolicy {

                key "PolicyName TunnelType TunnelID";

                leaf PolicyName {

                    type base:Basetype_String {

                        length "1..19";

                    }

                    description "Name of tunnel policy";

                }

                leaf TunnelType {

                    type enumeration {

                        enum 0;

                        enum 1;

                    }

                    description "Tunnel Type. Enumeration, 0—Tunnel, 1—TunnelBundle";

                }

                leaf TunnelID {

                    type base:Basetype_UnsignedInteger32;

                    description "Index column BUNDLE ID";

                }

            }

        }

        container LabelSegments {

            description "This table contains MPLS label segments information.";

            list LabelSegment {

                description "LabelSegment row name";

                key "ProtocolType";

                leaf ProtocolType {

                    type base:Basetype_UnsignedInteger32 {

                        range "0..8";

                    }

                    description "Protocol Type. Enumeration, 0—static";

                }

                leaf MinLabel {

                    type base:Basetype_UnsignedInteger32;

                    description "The minimum label of the segment.";

                }

                leaf MaxLabel {

                    type base:Basetype_UnsignedInteger32;

                    description "The maximum label of the segment.";

                }

            }

        }

        container TunnelMbfds {

            description "This table contains MPLS TunnelMbfd information.";

            list TunnelMbfd {

                description "TunnelMbfd row name";

                key "TunnelID";

                leaf TunnelID {

                    type base:Basetype_UnsignedInteger32;

                    description "Index column ID UnsignedInteger32";

                }

                leaf Enable {

                    type base:Basetype_Boolean;

                    description "BOOL_TRUE == enable BOOL_FALSE == unenable";

                }

                leaf Echo {

                    type base:Basetype_Boolean;

                    description "BOOL_TRUE == enable BOOL_FALSE == unenable";

                }

                leaf Template {

                    type base:Basetype_String {

                        length "1..63";

                    }

                    description "The bfd template name.";

                }

                leaf BackupTemplate {

                    type base:Basetype_String {

                        length "1..63";

                    }

                    description "The Backup bfd template name.";

                }

            }

        }

        container StaticSRLSPs {

            description "This table contains static SRingress LSP information.

                This table supports creating rows.";

            list StaticSRLSP {

                key "LSPName";

                leaf LSPName {

                    type base:Basetype_String {

                        length "1..15";

                    }

                    description "Index column string 1-15";

                }

                leaf-list OutLabel {

                    type base:Basetype_UnsignedInteger32;

                    description "LSP outgoing label";

                }

            }

        }

        container StaticSRAdjacencies {

            description "This table contains static SRtransit LSP information.

                This table supports creating rows.";

            list StaticSRAdjacency {

                key "AdjName";

                leaf AdjName {

                    type base:Basetype_String {

                        length "1..15";

                    }

                    description "Index column string 1-15";

                }

                leaf InLabel {

                    type base:Basetype_UnsignedInteger32;

                    description "LSP incoming label,The value range varies by device model.";

                }

                leaf NextHop {

                    type base:Basetype_Ipv4Address;

                    description "LSP next hop address";

                }

                leaf OutIfIndex {

                    type base:Basetype_NameAndIndexUnion;

                    description "LSP outgoing interface index";

                }

            }

        }

        container StaticSRPrefixs {

            description "This table contains static node segment routing prefix information.

                This table supports creating rows.";

            list StaticSRPrefix {

                description "SRPrefix row name Repeat Instance";

                key "PrefixName DestAddress DestMask InLabel NextHop OutIfIndex";

                leaf PrefixName {

                    type base:Basetype_String {

                        length "1..15";

                    }

                    description "Name of static segment routing Prefix";

                }

                leaf DestAddress {

                    type base:Basetype_Ipv4Address;

                    description "IPV4 prefix destination address";

                }

                leaf DestMask {

                    type base:Basetype_UnsignedInteger32 {

                        range "0..32";

                    }

                    description "Prefix destination address mask";

                }

                leaf InLabel {

                    type base:Basetype_UnsignedInteger32;

                    description "Prefix incoming label";

                }

                leaf NextHop {

                    type union {

                        type base:Basetype_EmptyString;

                        type base:Basetype_Ipv4Address;

                    }

                    description "Prefix next hop address";

                }

                leaf OutIfIndex {

                    type union {

                        type base:Basetype_EmptyString;

                        type base:Basetype_NameAndIndexUnion;

                    }

                    description "Prefix outgoing interface index";

                }

                leaf OutLabel {

                    type base:Basetype_UnsignedInteger32;

                    description "Prefix outgoing label";

                }

            }

        }

        container StaticEgressLSPs {

            description "This table contains static egress LSP information

                This table supports creating rows.";

            list StaticEgressLSP {

                description "StaticEgressLSP row name";

                key "LSPName";

                leaf LSPName {

                    type base:Basetype_String {

                        length "1..15";

                    }

                    description "Name of static LSP";

                }

                leaf InLabel {

                    type base:Basetype_UnsignedInteger32;

                    description "LSP incoming label,The value range varies by device model.";

                }

            }

        }

        container StaticIngressLSPs {

            description "This table contains static ingress LSP information.

                This table supports creating rows.";

            list StaticIngressLSP {

                key "LSPName";

                leaf LSPName {

                    type base:Basetype_String {

                        length "1..15";

                    }

                    description "Name of static LSP";

                }

                leaf OutLabel {

                    type base:Basetype_UnsignedInteger32;

                    description "LSP outgoing label";

                }

                leaf DestAddress {

                    type base:Basetype_Ipv4Address;

                    description "IPV4 LSP destination address";

                }

                leaf DestWildcardMask {

                    type base:Basetype_Ipv4Address;

                    description "Wildcard mask for DestAddress";

                }

                leaf NextHop {

                    type base:Basetype_Ipv4Address;

                    description "LSP next hop address";

                }

                leaf OutIfIndex {

                    type base:Basetype_NameAndIndexUnion;

                    description "LSP outgoing interface index";

                }

            }

        }

        container StaticTransitLSPs {

            description "This table contains static transit LSP information.

                This table supports creating rows.";

            list StaticTransitLSP {

                key "LSPName";

                leaf LSPName {

                    type base:Basetype_String {

                        length "1..15";

                    }

                    description "Name of static LSP";

                }

                leaf InLabel {

                    type base:Basetype_UnsignedInteger32;

                    description "LSP incoming label,The value range varies by device model.";

                }

                leaf OutLabel {

                    type base:Basetype_UnsignedInteger32;

                    description "LSP outgoing label";

                }

                leaf NextHop {

                    type base:Basetype_Ipv4Address;

                    description "LSP next hop address";

                }

                leaf OutIfIndex {

                    type base:Basetype_NameAndIndexUnion;

                    description "LSP outgoing interface index";

                }

            }

        }

        container MPLSVRFs {

            description "This table contains MPLS VRF information.

                This table supports creating rows.";

            list MPLSVRF {

                description "VRF row name";

                key "VRF";

                leaf VRF {

                    type base:Basetype_String {

                        length "1..31";

                    }

                    description "VRF name";

                }

                leaf Statistics {

                    type base:Basetype_Boolean;

                    description "Statistics for the VRF";

                }

            }

        }

        container SegmentRouting {

            description "MPLS segment routing table";

            container GlobalSRGB {

                description "Global SRGB configuration.";

                leaf Lowerbound {

                    type base:Basetype_UnsignedInteger32 {

                        range "16..1048574";

                    }

                    description "Lower bound of the global label block.";

                }

                leaf Upperbound {

                    type base:Basetype_UnsignedInteger32 {

                        range "17..1048575";

                    }

                    description "Upper bound of the global label block.";

                }

            }

            container SRLB {

                description "SR Local Block configuration.";

                leaf Lowerbound {

                    type base:Basetype_UnsignedInteger32 {

                        range "16..1048574";

                    }

                    description "Lower bound of the local label block.";

                }

                leaf Upperbound {

                    type base:Basetype_UnsignedInteger32 {

                        range "17..1048575";

                    }

                    description "Upper bound of the local label block.";

                }

            }

        }

    }

}
