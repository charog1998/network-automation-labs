module H3C-pppoes-config {

    namespace "http://www.h3c.com/netconf/config:1.0";

    prefix "pppoes-config";

    import comware-basetype {

         prefix "base";

    }

    import comware-extension {

         prefix "ext";

    }

    organization "NEW H3C Technologies Co., Ltd.";

    contact "Website: http://www.h3c.com";

    description "The module entities for pppoes config.";

    revision 2019-12-07 {

        description "Initial revision.";

    }

    container PPPOES {

        container PppoesBind {

            list BindVT {

                key "IfIndex";

                leaf IfIndex {

                    type base:Basetype_NameAndIndexUnion;

                }

                leaf VTNum {

                    type base:Basetype_UnsignedInteger32;

                }

            }

        }

        container PppoesIfLimit {

            list IfLimit {

                key "IfIndex";

                leaf IfIndex {

                    type base:Basetype_NameAndIndexUnion;

                }

                leaf LimitIf {

                    type base:Basetype_UnsignedInteger32 {

                        range "1..65534";

                    }

                }

                leaf LimitClnMac {

                    type base:Basetype_UnsignedInteger32 {

                        range "1..65534";

                    }

                }

            }

        }

    }

}
