module H3C-pbr-config {

    namespace "http://www.h3c.com/netconf/config:1.0";

    prefix "pbr-config";

    import comware-basetype {

         prefix "base";

    }

    import comware-extension {

         prefix "ext";

    }

    organization "NEW H3C Technologies Co., Ltd.";

    contact "Website: http://www.h3c.com";

    description "The module entities for pbr config.";

    revision 2019-12-07 {

        description "Synchronize the modification of the schema file to the YANG file.";

    }

    revision 2017-06-05 {

        description "Initial revision.";

    }

    container PBR {

        container PBRPolicyNode {

            list PolicyNode {

                key "AddressType PolicyName NodeID";

                leaf AddressType {

                    type enumeration {

                        enum 0;

                        enum 1;

                    }

                }

                leaf PolicyName {

                    type base:Basetype_String {

                        length "1..19";

                    }

                }

                leaf NodeID {

                    type base:Basetype_UnsignedInteger32 {

                        range "0..65535";

                    }

                }

                leaf Mode {

                    type enumeration {

                        enum 1;

                        enum 2;

                    }

                }

                leaf ACLNumber {

                    type base:Basetype_UnsignedInteger32 {

                        range "2000..3999";

                    }

                }

                leaf ACLName {

                    type base:Basetype_String {

                        pattern "[a-zA-Z][^?	

]{0,62}";

                    }

                }

                leaf MatchPacketLenMin {

                    type base:Basetype_UnsignedInteger32 {

                        range "1..65535";

                    }

                }

                leaf MatchPacketLenMax {

                    type base:Basetype_UnsignedInteger32 {

                        range "1..65535";

                    }

                }

                leaf ApplyPrecedence {

                    type enumeration {

                        enum 0;

                        enum 1;

                        enum 2;

                        enum 3;

                        enum 4;

                        enum 5;

                        enum 6;

                        enum 7;

                    }

                }

                leaf ApplyIPDF {

                    type enumeration {

                        enum 0;

                        enum 1;

                    }

                }

                leaf ApplyRemarkVPN {

                    type base:Basetype_Boolean;

                }

                leaf ApplyContinue {

                    type base:Basetype_Boolean;

                }

                leaf ApplyLoadShareNexthop {

                    type base:Basetype_Boolean;

                }

                leaf ApplyLoadShareDefNexthop {

                    type base:Basetype_Boolean;

                }

                leaf ApplyLoadShareInterface {

                    type base:Basetype_Boolean;

                }

                leaf ApplyLoadShareDefInterface {

                    type base:Basetype_Boolean;

                }

            }

        }

        container PBRIfPolicy {

            list IfPolicy {

                key "AddressType IfIndex";

                leaf AddressType {

                    type enumeration {

                        enum 0;

                        enum 1;

                    }

                }

                leaf IfIndex {

                    type base:Basetype_NameAndIndexUnion;

                }

                leaf PolicyName {

                    type base:Basetype_String {

                        length "1..19";

                    }

                }

            }

        }

        container PBRApplyNexthop {

            list ApplyNexthop {

                key "AddressType PolicyName NodeID Mode VrfIndex IpAddress";

                leaf AddressType {

                    type enumeration {

                        enum 0;

                        enum 1;

                    }

                }

                leaf PolicyName {

                    type base:Basetype_String {

                        length "1..19";

                    }

                }

                leaf NodeID {

                    type base:Basetype_UnsignedInteger32 {

                        range "0..65535";

                    }

                }

                leaf Mode {

                    type enumeration {

                        enum 0;

                        enum 1;

                    }

                }

                leaf VrfIndex {

                    type base:Basetype_NameAndIndexUnion;

                }

                leaf IpAddress {

                    type base:Basetype_IpAddress;

                }

                leaf TrackID {

                    type base:Basetype_UnsignedInteger32 {

                        range "1..1024";

                    }

                }

                leaf NexthopDirect {

                    type base:Basetype_Boolean;

                }

            }

        }

        container PBRApplyOutInterface {

            list ApplyOutInterface {

                key "AddressType PolicyName NodeID Mode IfIndex";

                leaf AddressType {

                    type enumeration {

                        enum 0;

                        enum 1;

                    }

                }

                leaf PolicyName {

                    type base:Basetype_String {

                        length "1..19";

                    }

                }

                leaf NodeID {

                    type base:Basetype_UnsignedInteger32 {

                        range "0..65535";

                    }

                }

                leaf Mode {

                    type enumeration {

                        enum 0;

                        enum 1;

                    }

                }

                leaf IfIndex {

                    type base:Basetype_NameAndIndexUnion;

                }

                leaf TrackID {

                    type base:Basetype_UnsignedInteger32 {

                        range "1..1024";

                    }

                }

            }

        }

        container PBRApplyAccessVPN {

            list ApplyAccessVPN {

                key "AddressType PolicyName NodeID VrfIndex";

                leaf AddressType {

                    type enumeration {

                        enum 0;

                        enum 1;

                    }

                }

                leaf PolicyName {

                    type base:Basetype_String {

                        length "1..19";

                    }

                }

                leaf NodeID {

                    type base:Basetype_UnsignedInteger32 {

                        range "0..65535";

                    }

                }

                leaf VrfIndex {

                    type base:Basetype_NameAndIndexUnion;

                }

            }

        }

        container PBRLocalPolicy {

            leaf Ipv4PolicyName {

                type base:Basetype_String {

                    length "1..19";

                }

            }

            leaf Ipv6PolicyName {

                type base:Basetype_String {

                    length "1..19";

                }

            }

        }

        container PBRApplicationGroup {

            list ApplicationGroup {

                key "AddressType PolicyName NodeID AppGroupName";

                leaf AddressType {

                    type enumeration {

                        enum 0;

                        enum 1;

                    }

                }

                leaf PolicyName {

                    type base:Basetype_String {

                        length "1..19";

                    }

                }

                leaf NodeID {

                    type base:Basetype_UnsignedInteger32 {

                        range "0..65535";

                    }

                }

                leaf AppGroupName {

                    type base:Basetype_String {

                        length "1..63";

                    }

                }

            }

        }

        container PBRObjectGroup {

            list ObjectGroup {

                key "AddressType PolicyName NodeID ObjectGroupName";

                leaf AddressType {

                    type enumeration {

                        enum 0;

                        enum 1;

                    }

                }

                leaf PolicyName {

                    type base:Basetype_String {

                        length "1..19";

                    }

                }

                leaf NodeID {

                    type base:Basetype_UnsignedInteger32 {

                        range "0..65535";

                    }

                }

                leaf ObjectGroupName {

                    type base:Basetype_String {

                        length "1..31";

                    }

                }

            }

        }

    }

}
